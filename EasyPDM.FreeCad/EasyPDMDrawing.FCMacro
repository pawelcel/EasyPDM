# -*- coding: utf-8 -*-
"""
EasyPDMDrawing -- FreeCAD macro that puts the EasyPDM drawing sheet on the active document's
TechDraw page and fills its title block from EasyPDM.

Install / run exactly like EasyPDMUpload.FCMacro (Macro -> Macros... -> add the folder, or
"Execute macro from file"). Login and API address are SHARED with the other EasyPDM macros
(User parameter:BaseApp/EasyPDM): being logged in to one is enough for all of them.

What it does, on the active document:
  1. Finds the EasyPDM item from the document's name -- the "number(name).REVISION" name the
     Upload macro gives a document after sending it. A document that is not in EasyPDM yet
     gets a message: send it with EasyPDM Upload first.
  2. Reads GET /api/items/{id}/title-block: labels in the project's main language, name and
     its translations (multilingual projects), drawing number, revision, material, mass,
     drawn by / approved by with dates (current revision only), processes, revision table,
     company name and logo.
  3. Pages: every TechDraw page that already uses an EasyPDM sheet (fields named pdm_*) is
     refreshed. A document without one gets a new page; if it has ordinary pages, the macro
     asks whether to put the EasyPDM sheet on the first of them (its views stay) or to add
     a new page.
  4. Builds the sheet: field values, the processes table above the title block (header at the
     bottom, rows growing upward, long text wrapping), the revision table in the top-right
     corner (header at the top, rows growing downward; revision A is not listed), the logo,
     the scale of the page and the sheet number ("2 / 3") -- recomputed on every run, because
     FreeCAD's own autofill only fills them once, when a template is inserted.

Running it again refreshes everything from EasyPDM, so values typed into pdm_* fields by hand
are overwritten; fields of a custom template that are not pdm_* keep what was typed.

Custom templates: any TechDraw SVG template works if it names its fields like the EasyPDM one
(pdm_name, pdm_drawn_by, pdm_label_name, ...; see templates/build_templates.py) -- and, for the
tables and the logo, has empty groups with the same ids and data-* positions.

The sheet the macro builds is written to <FreeCAD user data>/EasyPDM/sheets and set as the
page's template; FreeCAD keeps a copy inside the .FCStd, so the file on disk is only a
working copy.
"""

import base64
import glob
import json
import os
import re
import time
from datetime import datetime
from urllib import error, request

import FreeCAD as App

try:
    from PySide6 import QtCore, QtGui, QtWidgets
except ImportError:
    try:
        from PySide2 import QtCore, QtGui, QtWidgets
    except ImportError:
        from PySide import QtCore, QtGui
        from PySide import QtGui as QtWidgets


# ===== BEGIN SHARED (copied into EasyPDMDrawing.FCMacro by build_templates.py) =====
from xml.sax.saxutils import escape as _xml_escape

FREECAD_NS = "https://www.freecad.org/wiki/index.php?title=Svg_Namespace"
SHEET_TITLE_PREFIX = "EasyPDM drawing sheet"
SHEET_FONT = "osifont"  # ISO 3098 lettering shipped with FreeCAD (Mod/TechDraw/Resources/fonts)
ZONE_LETTERS = "ABCDEFGHJKLMNPQRSTUVWXYZ"
SHEET_FORMATS = {"A3": (420, 297)}

_THIN = "fill:none;stroke:#000000;stroke-width:0.35;stroke-linecap:round;stroke-linejoin:round"
_THICK = "fill:none;stroke:#000000;stroke-width:0.7;stroke-linecap:round;stroke-linejoin:round"

# Field labels in English; the macro overwrites them with the project's main language from
# the server's document labels (Settings -> Language -> Labels in documents, keys
# titleblock.*). Template field name -> server label key.
SHEET_LABELS = {
    "drawn_by": ("drawnBy", "DRAWN BY"),
    "drawn_date": ("date", "DATE"),
    "approved_by": ("approvedBy", "APPROVED BY"),
    "approved_date": ("date", "DATE"),
    "material": ("material", "MATERIAL"),
    "scale": ("scale", "SCALE"),
    "sheet": ("sheet", "SHEET"),
    "mass": ("mass", "MASS"),
    "company": ("company", "COMPANY"),
    "name": ("name", "NAME"),
    "drawing_number": ("drawingNumber", "DRAWING NUMBER"),
    "revision": ("revision", "REVISION"),
    "format": ("format", "FORMAT"),
}


def _f(v):
    return ("%.2f" % v).rstrip("0").rstrip(".")


def _esc(text):
    return _xml_escape(text or "", {'"': "&quot;"})


def approx_text_width(text, size):
    """Width in mm of `text` set in osifont at `size` mm -- a fallback for when Qt cannot
    measure (no GUI). osifont is narrow; 0.58 em per character errs on the wide side, so a
    line wraps a little early rather than running past its cell."""
    return len(text or "") * size * 0.58


def wrap_text(text, width, size, measure):
    """Splits `text` into lines no wider than `width` mm, at spaces; a single word longer
    than the line is left whole rather than cut mid-word."""
    lines = []
    for para in (text or "").splitlines() or [""]:
        line = ""
        for word in para.split(" "):
            candidate = word if not line else line + " " + word
            if line and measure(candidate, size) > width:
                lines.append(line)
                line = word
            else:
                line = candidate
        lines.append(line)
    while lines and lines[-1] == "":
        lines.pop()
    return lines


def wrap_joined(parts, width, size, measure, sep=" · "):
    """Translations as "EN: Cube · DE: Würfel": on one line while they fit, otherwise one
    language per line (each wrapped further if it is still too long)."""
    parts = [p for p in parts if p]
    if not parts:
        return []
    joined = sep.join(parts)
    if measure(joined, size) <= width:
        return [joined]
    lines = []
    for p in parts:
        lines.extend(wrap_text(p, width, size, measure))
    return lines


def _text(x, y, content, size, extra=""):
    return '<text x="%s" y="%s" style="font-size:%spx;fill:#000000%s">%s</text>' % (
        _f(x), _f(y), _f(size), extra, _esc(content))


def _line(x1, y1, x2, y2):
    return '<path d="M %s,%s L %s,%s"/>' % (_f(x1), _f(y1), _f(x2), _f(y2))


def build_base_sheet(fmt_name):
    """The bare template for one format: frame, grid reference, title block with empty
    pdm_* fields and the three empty groups."""
    W, H = SHEET_FORMATS[fmt_name]
    o = []
    add = o.append
    add('<g id="sheet" style="font-family:%s">' % SHEET_FONT)

    FL, FT, FR, FB = 20, 10, W - 10, H - 10      # drawing frame
    OL, OT, OR, OB = 15, 5, W - 5, H - 5         # outer line of the grid strip
    cx, cy = W / 2.0, H / 2.0
    add('<rect id="drawing_frame" x="%s" y="%s" width="%s" height="%s" style="%s"/>'
        % (FL, FT, _f(FR - FL), _f(FB - FT), _THICK))
    xs = [cx + 50 * k for k in range(-20, 21) if FL < cx + 50 * k < FR]
    ys = [cy + 50 * k for k in range(-20, 21) if FT < cy + 50 * k < FB]
    add('<g id="grid_reference" style="%s">' % _THIN)
    add('<rect x="%s" y="%s" width="%s" height="%s"/>' % (OL, OT, _f(OR - OL), _f(OB - OT)))
    for x in xs:
        add(_line(x, OT, x, FT))
        add(_line(x, FB, x, OB))
    for y in ys:
        add(_line(OL, y, FL, y))
        add(_line(FR, y, OR, y))
    add("</g>")
    cols, rows = [FL] + xs + [FR], [FT] + ys + [FB]
    add('<g id="grid_reference_markers" style="font-size:3.5px;text-anchor:middle;fill:#000000;stroke:none">')
    for i in range(len(cols) - 1):
        m = (cols[i] + cols[i + 1]) / 2
        for y in (OT + 3.75, FB + 3.75):
            add('<text x="%s" y="%s">%d</text>' % (_f(m), _f(y), i + 1))
    for i in range(len(rows) - 1):
        m = (rows[i] + rows[i + 1]) / 2 + 1.25
        for x in ((OL + FL) / 2.0, (FR + OR) / 2.0):
            add('<text x="%s" y="%s">%s</text>' % (_f(x), _f(m), ZONE_LETTERS[i]))
    add("</g>")
    add('<g id="centring_marks" style="%s">' % _THICK)
    add(_line(cx, 0, cx, FT + 5))
    add(_line(cx, H, cx, FB - 5))
    add(_line(0, cy, FL + 5, cy))
    add(_line(W, cy, FR - 5, cy))
    add("</g>")

    # Title block 180 x 44 mm in the bottom-right corner.
    x0, y0 = FR - 180, FB - 44
    X = lambda dx: x0 + dx
    Y = lambda dy: y0 + dy
    add('<g id="title_block_lines" style="%s">' % _THIN)
    add(_line(X(70), Y(0), X(70), Y(44)))
    for dy in (11, 22, 33):
        add(_line(X(0), Y(dy), X(70), Y(dy)))
    add(_line(X(46), Y(0), X(46), Y(22)))
    add(_line(X(22), Y(33), X(22), Y(44)))
    add(_line(X(40), Y(33), X(40), Y(44)))
    add(_line(X(70), Y(11), X(180), Y(11)))
    add(_line(X(70), Y(28), X(180), Y(28)))
    add(_line(X(163), Y(11), X(163), Y(28)))
    add(_line(X(140), Y(28), X(140), Y(44)))
    add(_line(X(162), Y(28), X(162), Y(44)))
    add("</g>")
    add('<rect id="title_block_frame" x="%s" y="%s" width="180" height="44" style="%s"/>'
        % (_f(x0), _f(y0), _THICK))

    def label(key, x, y):
        add('<text freecad:editable="pdm_label_%s" x="%s" y="%s" style="font-size:2px;fill:#000000">'
            "<tspan>%s</tspan></text>" % (key, _f(x), _f(y), _esc(SHEET_LABELS[key][1])))

    def value(key, x, y, size=3.5, text="", bold=False, anchor="start", autofill=None):
        style = "font-size:%spx;fill:#000000" % _f(size)
        if bold:
            style += ";font-weight:bold"
        if anchor != "start":
            style += ";text-anchor:%s" % anchor
        extra = ' freecad:autofill="%s"' % autofill if autofill else ""
        add('<text freecad:editable="pdm_%s"%s x="%s" y="%s" style="%s"><tspan>%s</tspan></text>'
            % (key, extra, _f(x), _f(y), style, _esc(text)))

    add('<g id="title_block_fields" style="fill:#000000;stroke:none">')
    label("drawn_by", X(1.5), Y(3));        value("drawn_by", X(1.5), Y(8.5))
    label("drawn_date", X(47.5), Y(3));     value("drawn_date", X(47.5), Y(8.5))
    label("approved_by", X(1.5), Y(14));    value("approved_by", X(1.5), Y(19.5))
    label("approved_date", X(47.5), Y(14)); value("approved_date", X(47.5), Y(19.5))
    label("material", X(1.5), Y(25));       value("material", X(1.5), Y(30.5))
    label("scale", X(1.5), Y(36));          value("scale", X(1.5), Y(41.5), text="1:1", autofill="scale")
    label("sheet", X(23.5), Y(36));         value("sheet", X(23.5), Y(41.5), text="1 / 1", autofill="sheet")
    label("mass", X(41.5), Y(36));          value("mass", X(41.5), Y(41.5))
    label("company", X(71.5), Y(3));        value("company", X(71.5), Y(8.8), bold=True)
    label("name", X(71.5), Y(14));          value("name", X(71.5), Y(21.5), size=6, bold=True)
    value("name_translations", X(71.5), Y(26.3), size=2.3)
    label("drawing_number", X(71.5), Y(31)); value("drawing_number", X(71.5), Y(40), size=5, bold=True)
    label("revision", X(141.5), Y(31));     value("revision", X(151), Y(41.5), size=7, bold=True, anchor="middle")
    label("format", X(163.5), Y(31));       value("format", X(171), Y(40.5), text=fmt_name, anchor="middle")
    add("</g>")

    add('<g id="pdm_logo" data-x="%s" data-y="%s" data-size="17"/>' % (_f(X(163)), _f(Y(11))))
    add('<g id="pdm_processes" data-x="%s" data-bottom="%s" data-width="180"/>' % (_f(x0), _f(y0)))
    add('<g id="pdm_revisions" data-right="%s" data-top="%s" data-width="160"/>' % (_f(FR), _f(FT)))
    add("</g>")

    return (
        '<?xml version="1.0" encoding="UTF-8" standalone="no"?>\n'
        '<!-- Generated by EasyPDM.FreeCad/templates/build_templates.py; do not edit by hand. -->\n'
        '<svg xmlns="http://www.w3.org/2000/svg" xmlns:xlink="http://www.w3.org/1999/xlink"'
        ' xmlns:freecad="%s" version="1.1"\n'
        '     width="%smm" height="%smm" viewBox="0 0 %s %s">\n'
        '  <title>%s %s landscape</title>\n'
        % (FREECAD_NS, _f(W), _f(H), _f(W), _f(H), SHEET_TITLE_PREFIX, fmt_name)
        + "\n".join("  " + p for p in o) + "\n</svg>\n"
    )


def _processes_table(x0, bottom, width, rows, headers, measure):
    """rows: [{"name", "description", "nameTr": [..], "descTr": [..]}] in the item's order;
    headers: (no, process, description). Header at the bottom, row 1 right above it."""
    w_no, w_name = 10.0, 60.0
    w_desc = width - w_no - w_name
    MAIN, SMALL, LH_MAIN, LH_SMALL, HDR = 3.4, 2.3, 3.6, 2.7, 6.0
    pad = 1.5
    built = []
    for i, r in enumerate(rows):
        name_l = wrap_text(r.get("name", ""), w_name - 2 * pad, MAIN, measure) or [""]
        desc_l = wrap_text(r.get("description", ""), w_desc - 2 * pad, MAIN, measure)
        ntr_l = wrap_joined(r.get("nameTr", []), w_name - 2 * pad, SMALL, measure)
        dtr_l = wrap_joined(r.get("descTr", []), w_desc - 2 * pad, SMALL, measure)
        h = 1.6 + LH_MAIN * max(len(name_l), len(desc_l), 1) + LH_SMALL * max(len(ntr_l), len(dtr_l)) + 0.8
        built.append((i + 1, name_l, desc_l, ntr_l, dtr_l, max(h, 6.0)))
    hdr_top = bottom - HDR
    top = hdr_top - sum(b[5] for b in built)
    o = ['<g style="%s">' % _THIN]
    o.append(_line(x0 + w_no, top, x0 + w_no, bottom))
    o.append(_line(x0 + w_no + w_name, top, x0 + w_no + w_name, bottom))
    o.append(_line(x0, hdr_top, x0 + width, hdr_top))
    yb = hdr_top
    for b in built:
        yt = yb - b[5]
        o.append(_line(x0, yt, x0 + width, yt))
        yb = yt
    o.append('</g><g style="%s">' % _THICK)
    o.append('<rect x="%s" y="%s" width="%s" height="%s"/>' % (_f(x0), _f(top), _f(width), _f(bottom - top)))
    o.append("</g>")
    o.append(_text(x0 + pad, hdr_top + 4.2, headers[0], 2.4, ";font-weight:bold"))
    o.append(_text(x0 + w_no + pad, hdr_top + 4.2, headers[1], 2.4, ";font-weight:bold"))
    o.append(_text(x0 + w_no + w_name + pad, hdr_top + 4.2, headers[2], 2.4, ";font-weight:bold"))
    yb = hdr_top
    for n, name_l, desc_l, ntr_l, dtr_l, h in built:
        yt = yb - h
        o.append(_text(x0 + w_no / 2.0, yt + 5.0, str(n), MAIN, ";text-anchor:middle"))
        for col_x, main_l, small_l in ((x0 + w_no + pad, name_l, ntr_l), (x0 + w_no + w_name + pad, desc_l, dtr_l)):
            y = yt + 4.4
            for line in main_l:
                o.append(_text(col_x, y, line, MAIN))
                y += LH_MAIN
            if not main_l:
                y += LH_MAIN
            y -= 0.6
            for line in small_l:
                o.append(_text(col_x, y, line, SMALL))
                y += LH_SMALL
        yb = yt
    return o


def _revisions_table(right, top, width, rows, headers, measure):
    """rows: [{"label", "date", "description", "by"}] oldest first; headers: (rev, date,
    description, by). Header at the top, rows growing downward."""
    x0 = right - width
    w_rev, w_date, w_by = 12.0, 22.0, 26.0
    w_desc = width - w_rev - w_date - w_by
    SIZE, LH, HDR, pad = 2.6, 3.2, 6.0, 1.5
    o_lines, o_text = [], []
    y = top + HDR
    o_lines.append(_line(x0, y, right, y))
    for r in rows:
        desc_l = wrap_text(r.get("description", ""), w_desc - 2 * pad, SIZE, measure) or [""]
        by_l = wrap_text(r.get("by", ""), w_by - 2 * pad, SIZE, measure) or [""]
        h = max(8.0, 3.0 + LH * max(len(desc_l), len(by_l)))
        o_text.append(_text(x0 + w_rev / 2.0, y + 5.3, r.get("label", ""), 3.4, ";font-weight:bold;text-anchor:middle"))
        o_text.append(_text(x0 + w_rev + pad, y + 5.3, r.get("date", ""), SIZE))
        for i, line in enumerate(desc_l):
            o_text.append(_text(x0 + w_rev + w_date + pad, y + 5.3 + i * LH, line, SIZE))
        for i, line in enumerate(by_l):
            o_text.append(_text(right - w_by + pad, y + 5.3 + i * LH, line, SIZE))
        y += h
        o_lines.append(_line(x0, y, right, y))
    bottom = y
    for cx in (x0 + w_rev, x0 + w_rev + w_date, right - w_by):
        o_lines.append(_line(cx, top, cx, bottom))
    o = ['<g style="%s">' % _THIN] + o_lines[:-1] + ["</g>"]
    o.append('<rect x="%s" y="%s" width="%s" height="%s" style="%s"/>' % (_f(x0), _f(top), _f(width), _f(bottom - top), _THICK))
    hx = (x0 + pad, x0 + w_rev + pad, x0 + w_rev + w_date + pad, right - w_by + pad)
    for x, h in zip(hx, headers):
        o.append(_text(x, top + 4.2, h, 2.4, ";font-weight:bold"))
    return o + o_text


def _group_attrs(svg, gid):
    m = re.search(r'<g\b([^>]*\bid="%s"[^>]*?)\s*/?>' % gid, svg)
    if not m:
        return None
    return dict(re.findall(r'data-([a-z]+)="([^"]*)"', m.group(1)))


def _replace_group(svg, gid, inner):
    """Puts `inner` into the empty or previously filled group `gid`. A filled group ends with
    a </g><!--/gid--> marker, so the old content is found again on the next refresh even
    though it contains nested groups."""
    m = re.search(r'<g\b([^>]*\bid="%s"[^>]*?)\s*/>' % gid, svg)
    if not m:
        m = re.search(r'<g\b([^>]*\bid="%s"[^>]*)>.*?</g><!--/%s-->' % (gid, gid), svg, re.S)
    if not m:
        return svg
    attrs = m.group(1).rstrip()
    new = ('<g%s/>' % attrs) if not inner else ('<g%s>%s</g><!--/%s-->' % (attrs, "".join(inner), gid))
    return svg[:m.start()] + new + svg[m.end():]


def fill_sheet(svg, values, processes=None, revisions=None, process_headers=None,
               revision_headers=None, logo_href=None, measure=None):
    """Writes `values` ({"pdm_name": "Kostka", "pdm_label_name": "NAZWA", ...}) into the
    matching freecad:editable texts and builds the tables and the logo into their groups.
    Works on the EasyPDM template and on any custom template that uses the same names; what
    a template does not have is simply skipped."""
    measure = measure or approx_text_width

    def fill(m):
        name = m.group(2)
        if name not in values:
            return m.group(0)
        return m.group(1) + "<tspan>%s</tspan>" % _esc(values[name]) + m.group(4)

    svg = re.sub(r'(<text\b[^>]*\bfreecad:editable="([^"]+)"[^>]*>)(.*?)(</text>)', fill, svg, flags=re.S)

    a = _group_attrs(svg, "pdm_processes")
    if a is not None:
        inner = []
        if processes:
            inner = _processes_table(float(a.get("x", 0)), float(a.get("bottom", 0)), float(a.get("width", 180)),
                                     processes, process_headers or ("No.", "PROCESS", "DESCRIPTION"), measure)
        svg = _replace_group(svg, "pdm_processes", inner)
    a = _group_attrs(svg, "pdm_revisions")
    if a is not None:
        inner = []
        if revisions:
            inner = _revisions_table(float(a.get("right", 0)), float(a.get("top", 0)), float(a.get("width", 160)),
                                     revisions, revision_headers or ("REV.", "DATE", "DESCRIPTION", "BY"), measure)
        svg = _replace_group(svg, "pdm_revisions", inner)
    a = _group_attrs(svg, "pdm_logo")
    if a is not None:
        inner = []
        if logo_href:
            size, pad = float(a.get("size", 17)), 1.5
            inner = ['<image x="%s" y="%s" width="%s" height="%s" preserveAspectRatio="xMidYMid meet" xlink:href="%s"/>'
                     % (_f(float(a.get("x", 0)) + pad), _f(float(a.get("y", 0)) + pad), _f(size - 2 * pad), _f(size - 2 * pad), logo_href)]
        svg = _replace_group(svg, "pdm_logo", inner)
    return svg
# ===== END SHARED =====


def _match_lang(raw):
    raw = (raw or "").strip().lower()
    if not raw:
        return None
    if raw.startswith("pl") or "polish" in raw or "polski" in raw:
        return "pl"
    if raw.startswith("de") or "german" in raw or "deutsch" in raw:
        return "de"
    if raw.startswith("en") or "english" in raw:
        return "en"
    return None


def _detect_language():
    """FreeCAD's own language setting first, then the operating system's locale; English
    when neither is Polish, English or German -- the same rule as the other EasyPDM macros."""
    try:
        raw = App.ParamGet("User parameter:BaseApp/Preferences/General").GetString("Language", "")
    except Exception:
        raw = ""
    return _match_lang(raw) or _match_lang(
        os.environ.get("LANGUAGE") or os.environ.get("LC_ALL") or os.environ.get("LANG") or "") or "en"


LANG = _detect_language()

TRANSLATIONS = {
    "pl": {
        "title": "Arkusz EasyPDM",
        "no_document": "Otwórz dokument części albo złożenia, dla którego ma powstać arkusz.",
        "not_in_pdm": "Dokument „{label}” nie jest jeszcze w EasyPDM.\n\nNajpierw wyślij go makrem EasyPDM Upload — po wysyłce dokument dostaje nazwę z numerem elementu, po której to makro go rozpoznaje.",
        "not_part": "Arkusz z tabelką mają tylko części i złożenia.",
        "ask_existing_page": "Dokument ma już stronę rysunku „{page}” bez arkusza EasyPDM.\n\nTak — użyj arkusza EasyPDM na tej stronie (widoki zostają).\nNie — dodaj nową stronę z arkuszem EasyPDM.",
        "new_page_label": "Rysunek",
        "done": "Tabelka wypełniona z EasyPDM ({pages}).",
        "failed": "Nie udało się przygotować arkusza:\n{error}",
        "no_connection": "Brak połączenia z {url}: {reason}",
        "login_failed_no_session": "Logowanie nie powiodło się — serwer nie zwrócił sesji.",
        "login_dialog_title": "Logowanie do PDM",
        "api_address_label": "Adres API:",
        "username_label": "Nazwa użytkownika:",
        "password_label": "Hasło:",
        "login_button": "Zaloguj",
        "cancel_button": "Anuluj",
        "login_missing_fields": "Podaj nazwę użytkownika i hasło.",
    },
    "en": {
        "title": "EasyPDM sheet",
        "no_document": "Open the part or assembly document the sheet is for.",
        "not_in_pdm": "Document \"{label}\" is not in EasyPDM yet.\n\nSend it with the EasyPDM Upload macro first — after sending, the document is named after its item number, which is how this macro recognises it.",
        "not_part": "Only parts and assemblies have a sheet with a title block.",
        "ask_existing_page": "The document already has the drawing page \"{page}\" without an EasyPDM sheet.\n\nYes — use the EasyPDM sheet on that page (its views stay).\nNo — add a new page with the EasyPDM sheet.",
        "new_page_label": "Drawing",
        "done": "Title block filled in from EasyPDM ({pages}).",
        "failed": "Could not prepare the sheet:\n{error}",
        "no_connection": "Could not connect to {url}: {reason}",
        "login_failed_no_session": "Login failed — the server did not return a session.",
        "login_dialog_title": "Log in to PDM",
        "api_address_label": "API address:",
        "username_label": "Username:",
        "password_label": "Password:",
        "login_button": "Log in",
        "cancel_button": "Cancel",
        "login_missing_fields": "Enter your username and password.",
    },
    "de": {
        "title": "EasyPDM-Blatt",
        "no_document": "Öffnen Sie das Teil- oder Baugruppendokument, für das das Blatt bestimmt ist.",
        "not_in_pdm": "Das Dokument „{label}“ ist noch nicht in EasyPDM.\n\nSenden Sie es zuerst mit dem Makro EasyPDM Upload — danach trägt das Dokument die Elementnummer im Namen, an der dieses Makro es erkennt.",
        "not_part": "Nur Teile und Baugruppen haben ein Blatt mit Schriftfeld.",
        "ask_existing_page": "Das Dokument hat bereits die Zeichnungsseite „{page}“ ohne EasyPDM-Blatt.\n\nJa — das EasyPDM-Blatt auf dieser Seite verwenden (die Ansichten bleiben).\nNein — eine neue Seite mit dem EasyPDM-Blatt hinzufügen.",
        "new_page_label": "Zeichnung",
        "done": "Schriftfeld aus EasyPDM ausgefüllt ({pages}).",
        "failed": "Das Blatt konnte nicht vorbereitet werden:\n{error}",
        "no_connection": "Keine Verbindung zu {url}: {reason}",
        "login_failed_no_session": "Anmeldung fehlgeschlagen — der Server hat keine Sitzung zurückgegeben.",
        "login_dialog_title": "Bei PDM anmelden",
        "api_address_label": "API-Adresse:",
        "username_label": "Benutzername:",
        "password_label": "Passwort:",
        "login_button": "Anmelden",
        "cancel_button": "Abbrechen",
        "login_missing_fields": "Geben Sie Benutzername und Passwort ein.",
    },
}


def t(key, **kwargs):
    text = TRANSLATIONS.get(LANG, TRANSLATIONS["en"]).get(key, TRANSLATIONS["en"].get(key, key))
    return text.format(**kwargs) if kwargs else text


# ---------------------------------------------------------------------------------------
# API access -- the same preferences, token and login as the other EasyPDM macros.
# ---------------------------------------------------------------------------------------
PARAM_GROUP = "User parameter:BaseApp/EasyPDM"
DEFAULT_BASE_URL = "http://localhost:5000/api"
SESSION_COOKIE_NAME = "pdm_session"


class AuthError(RuntimeError):
    pass


def get_base_url():
    return App.ParamGet(PARAM_GROUP).GetString("ApiBaseUrl", DEFAULT_BASE_URL).rstrip("/")


def set_base_url(url):
    App.ParamGet(PARAM_GROUP).SetString("ApiBaseUrl", url.rstrip("/"))


def get_session_token():
    return App.ParamGet(PARAM_GROUP).GetString("SessionToken", "") or None


def set_session_token(token):
    App.ParamGet(PARAM_GROUP).SetString("SessionToken", token or "")


def set_saved_username(name):
    App.ParamGet(PARAM_GROUP).SetString("SavedDisplayName", name or "")


def _auth_headers():
    token = get_session_token()
    return {"Cookie": "%s=%s" % (SESSION_COOKIE_NAME, token)} if token else {}


def _read_error_body(http_error):
    try:
        return http_error.read().decode("utf-8") or str(http_error)
    except Exception:
        return str(http_error)


def _get(path, binary=False):
    req = request.Request(get_base_url() + path, method="GET", headers=_auth_headers())
    try:
        with request.urlopen(req, timeout=30) as resp:
            data = resp.read()
            if binary:
                return data
            body = data.decode("utf-8")
            return json.loads(body) if body else None
    except error.HTTPError as e:
        if e.code == 401:
            raise AuthError(_read_error_body(e))
        raise RuntimeError(_read_error_body(e))
    except error.URLError as e:
        raise RuntimeError(t("no_connection", url=get_base_url(), reason=e.reason))


def api_get(path):
    return _get(path)


def api_get_binary(path):
    return _get(path, binary=True)


def api_login(username, password):
    """POST /api/auth/macro-login -- a separate, revocable macro token (falls back to the
    plain login on a server older than 0.8, like the other macros)."""
    data = json.dumps({"username": username, "password": password, "client": "FreeCAD Drawing"}).encode("utf-8")

    def _post(path):
        req = request.Request(get_base_url() + path, data=data, method="POST",
                              headers={"Content-Type": "application/json"})
        with request.urlopen(req, timeout=10) as resp:
            raw = resp.read().decode("utf-8")
            return (json.loads(raw) if raw else {}), resp.headers.get("Set-Cookie", "")

    try:
        try:
            user, cookie = _post("/auth/macro-login")
        except error.HTTPError as e:
            if e.code != 404:
                raise
            user, cookie = _post("/auth/login")
    except error.HTTPError as e:
        raise RuntimeError(_read_error_body(e))
    except error.URLError as e:
        raise RuntimeError(t("no_connection", url=get_base_url(), reason=e.reason))
    token = user.get("sessionToken") or None
    for part in ([] if token else cookie.split(";")):
        part = part.strip()
        if part.startswith(SESSION_COOKIE_NAME + "="):
            token = part[len(SESSION_COOKIE_NAME) + 1:]
            break
    if not token:
        raise RuntimeError(t("login_failed_no_session"))
    set_session_token(token)
    set_saved_username(user.get("displayName") or user.get("username") or username)
    return user


class LoginDialog(QtWidgets.QDialog):
    def __init__(self, parent=None):
        super().__init__(parent)
        self.setWindowTitle(t("login_dialog_title"))
        self.setMinimumWidth(360)
        layout = QtWidgets.QVBoxLayout(self)
        form = QtWidgets.QFormLayout()
        layout.addLayout(form)
        self.server_edit = QtWidgets.QLineEdit(get_base_url())
        form.addRow(t("api_address_label"), self.server_edit)
        self.username_edit = QtWidgets.QLineEdit()
        form.addRow(t("username_label"), self.username_edit)
        self.password_edit = QtWidgets.QLineEdit()
        self.password_edit.setEchoMode(QtWidgets.QLineEdit.Password)
        form.addRow(t("password_label"), self.password_edit)
        self.error_label = QtWidgets.QLabel("")
        self.error_label.setStyleSheet("color: #c0392b;")
        self.error_label.setWordWrap(True)
        layout.addWidget(self.error_label)
        buttons = QtWidgets.QDialogButtonBox(QtWidgets.QDialogButtonBox.Ok | QtWidgets.QDialogButtonBox.Cancel)
        buttons.button(QtWidgets.QDialogButtonBox.Ok).setText(t("login_button"))
        buttons.button(QtWidgets.QDialogButtonBox.Cancel).setText(t("cancel_button"))
        buttons.accepted.connect(self._try_login)
        buttons.rejected.connect(self.reject)
        layout.addWidget(buttons)

    def _try_login(self):
        self.error_label.setText("")
        set_base_url(self.server_edit.text().strip())
        username = self.username_edit.text().strip()
        password = self.password_edit.text()
        if not username or not password:
            self.error_label.setText(t("login_missing_fields"))
            return
        try:
            api_login(username, password)
        except Exception as e:
            self.error_label.setText(str(e))
            return
        self.accept()


def ensure_logged_in():
    if get_session_token():
        try:
            api_get("/auth/me")
            return True
        except AuthError:
            set_session_token(None)
        except Exception:
            return True
    return LoginDialog().exec() == QtWidgets.QDialog.Accepted


# ---------------------------------------------------------------------------------------
# Which EasyPDM item is this document -- the same rule as EasyPDMUpload.FCMacro.
# ---------------------------------------------------------------------------------------
_REVISION_NAME_PATTERN = re.compile(r"^(?P<prefix>[A-Za-z]*)(?P<number>\d+)\s*(?:\((?P<name>.+)\))?(?:\.[A-Za-z]+)?$")


def _record_key(text):
    return re.sub(r"\s+", "", text or "").lower()


def record_name_text(item):
    record = item.get("recordName")
    if record:
        return str(record)
    return "%s(%s)" % (item.get("itemNumberLabel") or item.get("itemNumber", ""), item.get("fileName", ""))


def label_matches_item(label, item):
    """The document label must be exactly the item's record name (plus an optional revision
    letter) -- the number alone would also match unrelated names like "testc2"."""
    base = re.sub(r"\.[A-Za-z]+$", "", label or "")
    return _record_key(base) == _record_key(record_name_text(item))


def find_item(doc):
    m = _REVISION_NAME_PATTERN.match(doc.Label or "")
    if not m:
        return None
    try:
        item = api_get("/items/by-number/%d" % int(m.group("number")))
    except AuthError:
        raise
    except Exception:
        return None
    return item if item and label_matches_item(doc.Label, item) else None


# ---------------------------------------------------------------------------------------
# Building the sheet
# ---------------------------------------------------------------------------------------
def _qt_measure():
    """Text width from the real osifont metrics when Qt is available (inside FreeCAD's GUI),
    so wrapping matches what TechDraw draws; the shared approximation otherwise."""
    try:
        font_path = os.path.join(App.getResourceDir(), "Mod", "TechDraw", "Resources", "fonts", "osifont-lgpl3fe.ttf")
        families = []
        if os.path.exists(font_path):
            fid = QtGui.QFontDatabase.addApplicationFont(font_path)
            families = QtGui.QFontDatabase.applicationFontFamilies(fid) if fid >= 0 else []
        if not families:
            return approx_text_width
        font = QtGui.QFont(families[0])
        font.setPixelSize(100)
        metrics = QtGui.QFontMetricsF(font)
        advance = getattr(metrics, "horizontalAdvance", None) or metrics.width
        return lambda text, size: advance(text or "") * size / 100.0
    except Exception:
        return approx_text_width


def _local_date(iso):
    """"2026-11-12T09:14:03.5Z" -> "2026-11-12" in the computer's own time zone."""
    if not iso:
        return ""
    try:
        s = iso.replace("Z", "+00:00")
        s = re.sub(r"\.(\d{6})\d+", r".\1", s)
        dt = datetime.fromisoformat(s)
        if dt.tzinfo is not None:
            dt = dt.astimezone()
        return dt.strftime("%Y-%m-%d")
    except Exception:
        return iso[:10]


def _scale_text(scale):
    try:
        s = float(scale)
    except Exception:
        return "1:1"
    if s <= 0:
        return "1:1"
    if s < 1:
        return "1:%s" % ("%g" % round(1.0 / s, 3))
    return "%s:1" % ("%g" % round(s, 3))


def _logo_href(tb):
    company = tb.get("company") or {}
    if not company.get("hasLogo"):
        return None
    try:
        data = api_get_binary("/settings/company/logo")
    except Exception:
        return None
    mime = "image/png" if data[:4] == b"\x89PNG" else "image/jpeg" if data[:2] == b"\xff\xd8" else None
    if not mime:
        return None
    return "data:%s;base64,%s" % (mime, base64.b64encode(data).decode("ascii"))


def sheet_values(tb, page_scale, sheet_no, sheet_count):
    labels = tb.get("labels") or {}
    v = {}
    for field, (key, english) in SHEET_LABELS.items():
        v["pdm_label_" + field] = (labels.get(key) or english).upper()
    drawn = tb.get("drawnBy") or {}
    approved = tb.get("approvedBy") or {}
    company = tb.get("company") or {}
    mass = tb.get("mass")
    v.update({
        "pdm_drawn_by": drawn.get("name") or "",
        "pdm_drawn_date": _local_date(drawn.get("at")),
        "pdm_approved_by": approved.get("name") or "",
        "pdm_approved_date": _local_date(approved.get("at")),
        "pdm_material": tb.get("material") or "",
        "pdm_mass": ("%s kg" % mass) if mass else "",
        "pdm_company": company.get("name") or "",
        "pdm_name": tb.get("name") or "",
        "pdm_name_translations": " · ".join(
            "%s: %s" % (x.get("languageCode"), x.get("name")) for x in tb.get("nameTranslations") or []),
        "pdm_drawing_number": tb.get("drawingNumber") or "",
        "pdm_revision": tb.get("revisionLabel") or "",
        "pdm_scale": _scale_text(page_scale),
        "pdm_sheet": "%d / %d" % (sheet_no, sheet_count),
    })
    return v


def sheet_tables(tb):
    labels = tb.get("labels") or {}
    lab = lambda k, d: (labels.get(k) or d).upper()
    processes = []
    for p in tb.get("processes") or []:
        tr = p.get("translations") or []
        processes.append({
            "name": p.get("name") or "",
            "description": p.get("description") or "",
            "nameTr": ["%s: %s" % (x.get("languageCode"), x.get("name")) for x in tr if x.get("name")],
            "descTr": ["%s: %s" % (x.get("languageCode"), x.get("description")) for x in tr if x.get("description")],
        })
    revisions = [{
        "label": r.get("revisionLabel") or "",
        "date": _local_date(r.get("at")),
        "description": r.get("description") or "",
        "by": r.get("by") or "",
    } for r in tb.get("revisions") or []]
    return (processes, revisions,
            (lab("processNo", "No."), lab("process", "Process"), lab("processDescription", "Description")),
            (lab("revisionLetter", "Rev."), lab("revisionDate", "Date"), lab("revisionDescription", "Change description"), lab("revisionBy", "By")))


def _is_pdm_template(tpl):
    try:
        return any(k.startswith("pdm_") for k in dict(tpl.EditableTexts))
    except Exception:
        return False


def _template_text(tpl):
    for path in (getattr(tpl, "Template", ""), getattr(tpl, "PageResult", "")):
        if path and os.path.exists(path):
            with open(path, encoding="utf-8") as f:
                return f.read()
    return ""


def _sheets_dir():
    d = os.path.join(App.getUserAppDataDir(), "EasyPDM", "sheets")
    os.makedirs(d, exist_ok=True)
    return d


def _write_sheet(doc, page, svg):
    """A new file name on every refresh: FreeCAD reloads a template only when the path
    changes. Older working copies of the same page are removed."""
    prefix = re.sub(r"[^A-Za-z0-9_-]+", "_", "%s_%s" % (doc.Name, page.Name))
    d = _sheets_dir()
    for old in glob.glob(os.path.join(d, prefix + "_*.svg")):
        try:
            os.remove(old)
        except OSError:
            pass
    path = os.path.join(d, "%s_%d.svg" % (prefix, int(time.time() * 1000)))
    with open(path, "w", encoding="utf-8", newline="\n") as f:
        f.write(svg)
    return path


def refresh_page(doc, page, tb, sheet_no, sheet_count, logo_href, measure, fmt_name="A3"):
    tpl = page.Template
    current = _template_text(tpl) if tpl is not None else ""
    own = (not current) or (SHEET_TITLE_PREFIX in current)
    if own:
        m = re.search(re.escape(SHEET_TITLE_PREFIX) + r" (\w+)", current or "")
        fmt_name = m.group(1) if m and m.group(1) in SHEET_FORMATS else fmt_name
        base = build_base_sheet(fmt_name)
    else:
        base = current
    old_texts = dict(tpl.EditableTexts) if tpl is not None else {}

    values = sheet_values(tb, getattr(page, "Scale", 1.0), sheet_no, sheet_count)
    if not own:
        values.pop("pdm_label_format", None)
    processes, revisions, p_head, r_head = sheet_tables(tb)
    svg = fill_sheet(base, values, processes, revisions, p_head, r_head, logo_href, measure)

    if tpl is None:
        tpl = doc.addObject("TechDraw::DrawSVGTemplate", "EasyPDMTemplate")
        page.Template = tpl
    tpl.Template = _write_sheet(doc, page, svg)
    texts = dict(tpl.EditableTexts)
    for k, val in old_texts.items():
        if not k.startswith("pdm_") and k in texts:
            texts[k] = val     # custom fields keep what was typed into them
    for k, val in values.items():
        if k in texts:
            texts[k] = val
    tpl.EditableTexts = texts


def _pages(doc):
    return [o for o in doc.Objects if o.TypeId == "TechDraw::DrawPage"]


def refresh_document(doc, ask_existing_page=None):
    """Fills every EasyPDM page of `doc`; creates one when there is none. `ask_existing_page`
    is called with the first ordinary page when the document has pages but no EasyPDM one,
    and returns True (use it), False (add a new page) or None (cancel)."""
    item = find_item(doc)
    if item is None:
        raise LookupError(t("not_in_pdm", label=doc.Label))
    tb = api_get("/items/%s/title-block" % item["id"])

    pages = _pages(doc)
    targets = [p for p in pages if p.Template is not None and _is_pdm_template(p.Template)]
    created = None
    if not targets:
        reuse = False
        if pages and ask_existing_page is not None:
            reuse = ask_existing_page(pages[0])
            if reuse is None:
                return None
        if reuse:
            old = pages[0].Template
            tpl = doc.addObject("TechDraw::DrawSVGTemplate", "EasyPDMTemplate")
            pages[0].Template = tpl
            if old is not None and not old.InList:
                doc.removeObject(old.Name)
            targets = [pages[0]]
        else:
            created = doc.addObject("TechDraw::DrawPage", "EasyPDMDrawing")
            created.Label = t("new_page_label")
            tpl = doc.addObject("TechDraw::DrawSVGTemplate", "EasyPDMTemplate")
            created.Template = tpl
            targets = [created]

    all_pages = _pages(doc)
    logo = _logo_href(tb)
    measure = _qt_measure()
    for page in targets:
        refresh_page(doc, page, tb, all_pages.index(page) + 1, len(all_pages), logo, measure)
    doc.recompute()
    return targets, created


def main():
    import FreeCADGui as Gui

    mw = Gui.getMainWindow()
    doc = App.ActiveDocument
    if doc is None:
        QtWidgets.QMessageBox.information(mw, t("title"), t("no_document"))
        return
    if not ensure_logged_in():
        return

    def ask(page):
        r = QtWidgets.QMessageBox.question(
            mw, t("title"), t("ask_existing_page", page=page.Label),
            QtWidgets.QMessageBox.Yes | QtWidgets.QMessageBox.No | QtWidgets.QMessageBox.Cancel,
            QtWidgets.QMessageBox.Yes)
        if r == QtWidgets.QMessageBox.Cancel:
            return None
        return r == QtWidgets.QMessageBox.Yes

    try:
        try:
            result = refresh_document(doc, ask)
        except AuthError:
            set_session_token(None)
            if not ensure_logged_in():
                return
            result = refresh_document(doc, ask)
    except LookupError as e:
        QtWidgets.QMessageBox.information(mw, t("title"), str(e))
        return
    except Exception as e:
        QtWidgets.QMessageBox.warning(mw, t("title"), t("failed", error=e))
        return
    if result is None:
        return
    targets, created = result
    if created is not None:
        try:
            created.ViewObject.doubleClicked()
        except Exception:
            pass
    msg = t("done", pages=", ".join(p.Label for p in targets))
    App.Console.PrintMessage("EasyPDM: %s\n" % msg)
    try:
        mw.statusBar().showMessage(msg, 8000)
    except Exception:
        pass


if __name__ == "__main__" and App.GuiUp:
    main()
