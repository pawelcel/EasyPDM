# -*- coding: utf-8 -*-
"""
EasyPDMDownload — makro FreeCAD do OTWIERANIA Części/Złożeń z EasyPDM (pobiera z serwera
i od razu otwiera w FreeCAD).

Instalacja / uruchomienie: dokładnie jak EasyPDMUpload.FCMacro — Macro -> Macros... ->
"Add path to macro path list", albo "Execute macro from file" bezpośrednio na tym pliku.
Logowanie i adres API są WSPÓLNE z EasyPDMUpload.FCMacro (te same preferencje FreeCAD,
User parameter:BaseApp/EasyPDM) — zalogowanie się w jednym makrze starcza dla obu. Makro
potrzebuje własnej sesji, mimo że wybór elementu zapada w przeglądarce — to ono odpytuje,
czy przeglądarka już skończyła (GET /api/create-tickets/{ticket}), i to ono ściąga same
pliki (GET /api/attachments/{id}/file) — przeglądarka tylko WSKAZUJE co pobrać, nie
przesyła żadnych bajtów. Ta sama sesja loguje przeglądarkę automatycznie (GET
/api/auth/browser-login) — jedno logowanie w makrze, nie dwa osobne.

Co robi:
    1. Natywne okno pyta TYLKO o folder docelowy (domyślnie podpowiada ostatnio użyty,
       zapamiętany w preferencjach FreeCAD, z przyciskiem "..." do zmiany) i pokazuje
       konto/Wyloguj — dokładnie jak "Wyślij do PDM" w EasyPDMUpload.FCMacro. WYBÓR,
       KTÓRĄ Część/Złożenie pobrać, zapada w PRZEGLĄDARCE SYSTEMOWEJ, nie tutaj: po
       zatwierdzeniu folderu makro od razu otwiera przeglądarkę, już zalogowaną (jednorazowy
       bilet logowania, nie sam token sesji makra), na pasku "oczekuje żądanie pobrania z makra CAD" (widoczny na
       każdym ekranie aplikacji webowej) z wyszukiwarką Części/Złożenia z CAŁEJ bazy (po
       numerze albo nazwie) — ten sam mechanizm co dogrywanie pliku do istniejącego
       elementu w EasyPDMUpload.FCMacro, tu użyty do wskazania "co pobrać". Po zatwierdzeniu
       w przeglądarce, FreeCAD (okno "Czekam na przeglądarkę", odpytujące co ~2s, limit
       10 minut) samo wykrywa wybór i pobieranie zaczyna się automatycznie — nie trzeba
       wracać do FreeCAD ręcznie. Anulowanie w przeglądarce/oknie oczekiwania kończy makro
       bez pobierania niczego.
    2. Dla Złożenia: pobiera też WSZYSTKIE jego składniki rekurencyjnie (bezpośrednie dzieci,
       potem ich dzieci, i tak dalej — cały BOM), do TEGO SAMEGO folderu co plik główny.
       Bez tego złożenie zbudowane na odnośnikach App::Link do zewnętrznych, zapisanych
       plików (standard w workbenchu Assembly/Assembly4) nie miałoby czym się otworzyć —
       FreeCAD rozwiązuje te odnośniki dopiero przy otwieraniu dokumentu, więc pliki
       składników muszą już leżeć na dysku PRZED otwarciem pliku głównego.
    3. Dla każdego pliku: jeśli w folderze docelowym jest już plik o DOKŁADNIE tej samej
       nazwie (czyli tej samej rewizji) i tym samym rozmiarze co na serwerze — pomija
       (nie pobiera drugi raz).
    4. Jeśli w folderze jest już plik tego samego elementu, ale w INNEJ (starszej) rewizji,
       a na serwerze jest nowsza — pyta, czy pobrać nowszą, zamiast cicho nadpisywać albo
       cicho zostawiać nieaktualny plik.
    5. Na końcu otwiera główny (wybrany) plik w FreeCAD (App.openDocument) — pliki składników
       zostają tylko na dysku, nie są automatycznie otwierane jako osobne dokumenty (dokładnie
       tak, jak FreeCAD sam otwiera złożenie: linkowane pliki wczytuje w tle, bez oddzielnych
       okien).

Skąd bierze pliki do pobrania:
    EasyPDM przechowuje AKTUALNY plik CAD Części/Złożenia jako załącznik (nie ma osobnego
    mechanizmu "plik elementu") — a przy KAŻDEJ wysyłce nowej rewizji poprzednia kopia
    ZOSTAJE (nowy załącznik obok starego, różne nazwy: "numer (nazwa).REWIZJA.rozszerzenie",
    ta sama konwencja co EasyPDMUpload.FCMacro), więc historia rewizji jest w praktyce
    odtwarzalna z listy załączników. To makro rozpoznaje tę konwencję, żeby trafić w
    załącznik odpowiadający AKTUALNEJ rewizji elementu (item["revisionNumber"]) — jeśli
    element nigdy nie przeszedł przez żadne makro CAD (np. dograny ręcznie w aplikacji
    webowej, więc załączniki mają dowolne, oryginalne nazwy), bierze po prostu najnowiej
    wgrany załącznik jako najlepsze przybliżenie.

Ograniczenia (świadomie poza zakresem pierwszej wersji):
    - Wybór elementu (punkt 1) wymaga, żeby domyślna przeglądarka systemowa umiała otworzyć
      adres serwera PDM (ten sam, co adres API w preferencjach makra) — na typowej
      instalacji (klient i serwer w tej samej sieci) działa to bez dodatkowej konfiguracji.
      Okno oczekiwania w FreeCAD ma limit 10 minut — po przekroczeniu (albo Anuluj) makro
      kończy się bez pobierania niczego.
    - Nie próbuje pobierać KONKRETNEJ starszej rewizji — zawsze celuje w aktualną, a starsze
      lokalne kopie służą tylko do wykrycia "masz nieaktualną wersję" (patrz punkt 4).
    - Wszystkie pliki (główny + składniki) lądują płasko w JEDNYM folderze, bez odtwarzania
      struktury BOM jako podfolderów — to najbezpieczniejszy wybór dla odnośników App::Link
      zapisanych jako ścieżki WZGLĘDEM folderu dokumentu (typowe dla Assembly4), ale jeśli
      oryginalny model był budowany z plikami w osobnych podfolderach, odnośniki mogą mimo
      to nie rozwiązać się automatycznie — wtedy trzeba je poprawić ręcznie w FreeCAD
      (Assembly4 ma do tego narzędzie "Make link relative"/zmianę ścieżki).
    - Współdzielony komponent (użyty w kilku miejscach drzewa) pobierany jest tylko raz
      (rozpoznawany po ID elementu), tak samo jak w EasyPDMUpload.FCMacro.
"""

import json
import os
import re
import shutil
import subprocess
import sys
import tempfile
import zipfile
import uuid
import webbrowser
from urllib import error, request
from urllib.parse import urlencode

import FreeCAD as App

try:
    from PySide6 import QtCore, QtWidgets
except ImportError:
    try:
        from PySide2 import QtCore, QtWidgets
    except ImportError:
        from PySide import QtCore
        from PySide import QtGui as QtWidgets  # bardzo stare FreeCAD (Qt4)


# ===== BEGIN SHARED (copied into EasyPDMUpload.FCMacro and EasyPDMDownload.FCMacro by templates/build_templates.py; edit it there) =====
import base64 as _sh_base64
import glob as _sh_glob
import time as _sh_time
from datetime import datetime as _sh_datetime
from xml.sax.saxutils import escape as _xml_escape

FREECAD_NS = "https://www.freecad.org/wiki/index.php?title=Svg_Namespace"
SHEET_TITLE_PREFIX = "EasyPDM drawing sheet"
SHEET_FONT = "osifont"  # ISO 3098 lettering shipped with FreeCAD (Mod/TechDraw/Resources/fonts)
ZONE_LETTERS = "ABCDEFGHJKLMNPQRSTUVWXYZ"
# Landscape formats: width, height (mm) and the number of grid reference fields across and
# down, as ISO 5457 sets them. The fields are 50 mm, laid out symmetrically from the centre
# lines, so the outermost ones absorb the remainder (A1: 50.5 mm at the left) instead of
# leaving a sliver next to the frame.
SHEET_FORMATS = {
    "A3": (420, 297, 8, 6),
    "A2": (594, 420, 12, 8),
    "A1": (841, 594, 16, 12),
}

_THIN = "fill:none;stroke:#000000;stroke-width:0.35;stroke-linecap:round;stroke-linejoin:round"
_THICK = "fill:none;stroke:#000000;stroke-width:0.7;stroke-linecap:round;stroke-linejoin:round"

# Field labels in English; the macro overwrites them with the project's main language from
# the server's document labels (Settings -> Language -> Labels in documents, keys
# titleblock.*). Template field name -> server label key.
SHEET_LABELS = {
    "drawn_by": ("drawnBy", "DRAWN BY"),
    "drawn_date": ("date", "DATE"),
    "approved_by": ("approvedBy", "APPROVED BY"),
    "approved_date": ("date", "DATE"),
    "material": ("material", "MATERIAL"),
    "scale": ("scale", "SCALE"),
    "sheet": ("sheet", "SHEET"),
    "mass": ("mass", "MASS"),
    "company": ("company", "COMPANY"),
    "name": ("name", "NAME"),
    "drawing_number": ("drawingNumber", "DRAWING NUMBER"),
    "revision": ("revision", "REVISION"),
    "format": ("format", "FORMAT"),
}


def _sh_f(v):
    return ("%.2f" % v).rstrip("0").rstrip(".")


def _sh_esc(text):
    return _xml_escape(text or "", {'"': "&quot;"})


def approx_text_width(text, size):
    """Width in mm of `text` set in osifont at `size` mm -- a fallback for when Qt cannot
    measure (no GUI). osifont is narrow; 0.58 em per character errs on the wide side, so a
    line wraps a little early rather than running past its cell."""
    return len(text or "") * size * 0.58


def wrap_text(text, width, size, measure):
    """Splits `text` into lines no wider than `width` mm, at spaces; a single word longer
    than the line is left whole rather than cut mid-word."""
    lines = []
    for para in (text or "").splitlines() or [""]:
        line = ""
        for word in para.split(" "):
            candidate = word if not line else line + " " + word
            if line and measure(candidate, size) > width:
                lines.append(line)
                line = word
            else:
                line = candidate
        lines.append(line)
    while lines and lines[-1] == "":
        lines.pop()
    return lines


def wrap_joined(parts, width, size, measure, sep=" · "):
    """Translations as "EN: Cube · DE: Würfel": on one line while they fit, otherwise one
    language per line (each wrapped further if it is still too long)."""
    parts = [p for p in parts if p]
    if not parts:
        return []
    joined = sep.join(parts)
    if measure(joined, size) <= width:
        return [joined]
    lines = []
    for p in parts:
        lines.extend(wrap_text(p, width, size, measure))
    return lines


def _sh_text(x, y, content, size, extra=""):
    return '<text x="%s" y="%s" style="font-size:%spx;fill:#000000%s">%s</text>' % (
        _sh_f(x), _sh_f(y), _sh_f(size), extra, _sh_esc(content))


def _sh_line(x1, y1, x2, y2):
    return '<path d="M %s,%s L %s,%s"/>' % (_sh_f(x1), _sh_f(y1), _sh_f(x2), _sh_f(y2))


def build_base_sheet(fmt_name, rec=None):
    """The bare template for one format: frame, grid reference, title block with empty
    pdm_* fields and the three empty groups.

    `rec`, when given ({"lines": [], "texts": [], "anchors": {}}), also receives every line
    (x1, y1, x2, y2, width) and text (x, baseline_y, text, size, bold, anchor, field) in mm,
    y down from the top edge -- what build_templates.py turns into the SolidWorks macro that
    draws the same sheet format."""
    W, H, fields_x, fields_y = SHEET_FORMATS[fmt_name]
    o = []
    add = o.append

    def ln(x1, y1, x2, y2, width):
        if rec is not None:
            rec["lines"].append((x1, y1, x2, y2, width))
        return _sh_line(x1, y1, x2, y2)

    def box(x, y, w, h, width):
        if rec is not None:
            for seg in ((x, y, x + w, y), (x + w, y, x + w, y + h), (x + w, y + h, x, y + h), (x, y + h, x, y)):
                rec["lines"].append(seg + (width,))

    def txt(x, y, text, size, bold=False, anchor="start", field=None):
        if rec is not None:
            rec["texts"].append((x, y, text, size, bold, anchor, field))
    add('<g id="sheet" style="font-family:%s">' % SHEET_FONT)

    FL, FT, FR, FB = 20, 10, W - 10, H - 10      # drawing frame
    OL, OT, OR, OB = 15, 5, W - 5, H - 5         # outer line of the grid strip
    cx, cy = W / 2.0, H / 2.0
    box(FL, FT, FR - FL, FB - FT, 0.7)
    add('<rect id="drawing_frame" x="%s" y="%s" width="%s" height="%s" style="%s"/>'
        % (FL, FT, _sh_f(FR - FL), _sh_f(FB - FT), _THICK))
    xs = [cx + 50 * k for k in range(-(fields_x // 2 - 1), fields_x // 2)]
    ys = [cy + 50 * k for k in range(-(fields_y // 2 - 1), fields_y // 2)]
    add('<g id="grid_reference" style="%s">' % _THIN)
    box(OL, OT, OR - OL, OB - OT, 0.35)
    add('<rect x="%s" y="%s" width="%s" height="%s"/>' % (OL, OT, _sh_f(OR - OL), _sh_f(OB - OT)))
    for x in xs:
        add(ln(x, OT, x, FT, 0.35))
        add(ln(x, FB, x, OB, 0.35))
    for y in ys:
        add(ln(OL, y, FL, y, 0.35))
        add(ln(FR, y, OR, y, 0.35))
    add("</g>")
    cols, rows = [FL] + xs + [FR], [FT] + ys + [FB]
    add('<g id="grid_reference_markers" style="font-size:3.5px;text-anchor:middle;fill:#000000;stroke:none">')
    for i in range(len(cols) - 1):
        m = (cols[i] + cols[i + 1]) / 2
        for y in (OT + 3.75, FB + 3.75):
            txt(m, y, str(i + 1), 3.5, anchor="middle")
            add('<text x="%s" y="%s">%d</text>' % (_sh_f(m), _sh_f(y), i + 1))
    for i in range(len(rows) - 1):
        m = (rows[i] + rows[i + 1]) / 2 + 1.25
        for x in ((OL + FL) / 2.0, (FR + OR) / 2.0):
            txt(x, m, ZONE_LETTERS[i], 3.5, anchor="middle")
            add('<text x="%s" y="%s">%s</text>' % (_sh_f(x), _sh_f(m), ZONE_LETTERS[i]))
    add("</g>")
    add('<g id="centring_marks" style="%s">' % _THICK)
    add(ln(cx, 0, cx, FT + 5, 0.7))
    add(ln(cx, H, cx, FB - 5, 0.7))
    add(ln(0, cy, FL + 5, cy, 0.7))
    add(ln(W, cy, FR - 5, cy, 0.7))
    add("</g>")

    # Title block 180 x 44 mm in the bottom-right corner.
    x0, y0 = FR - 180, FB - 44
    X = lambda dx: x0 + dx
    Y = lambda dy: y0 + dy
    add('<g id="title_block_lines" style="%s">' % _THIN)
    add(ln(X(70), Y(0), X(70), Y(44), 0.35))
    for dy in (11, 22, 33):
        add(ln(X(0), Y(dy), X(70), Y(dy), 0.35))
    add(ln(X(46), Y(0), X(46), Y(22), 0.35))
    add(ln(X(22), Y(33), X(22), Y(44), 0.35))
    add(ln(X(40), Y(33), X(40), Y(44), 0.35))
    add(ln(X(70), Y(11), X(180), Y(11), 0.35))
    add(ln(X(70), Y(28), X(180), Y(28), 0.35))
    add(ln(X(163), Y(11), X(163), Y(28), 0.35))
    add(ln(X(140), Y(28), X(140), Y(44), 0.35))
    add(ln(X(162), Y(28), X(162), Y(44), 0.35))
    add("</g>")
    box(x0, y0, 180, 44, 0.7)
    add('<rect id="title_block_frame" x="%s" y="%s" width="180" height="44" style="%s"/>'
        % (_sh_f(x0), _sh_f(y0), _THICK))

    def label(key, x, y):
        txt(x, y, SHEET_LABELS[key][1], 2.0, field="pdm_label_" + key)
        add('<text freecad:editable="pdm_label_%s" x="%s" y="%s" style="font-size:2px;fill:#000000">'
            "<tspan>%s</tspan></text>" % (key, _sh_f(x), _sh_f(y), _sh_esc(SHEET_LABELS[key][1])))

    def value(key, x, y, size=3.5, text="", bold=False, anchor="start", autofill=None):
        style = "font-size:%spx;fill:#000000" % _sh_f(size)
        if bold:
            style += ";font-weight:bold"
        if anchor != "start":
            style += ";text-anchor:%s" % anchor
        txt(x, y, text, size, bold, anchor, "pdm_" + key)
        extra = ' freecad:autofill="%s"' % autofill if autofill else ""
        add('<text freecad:editable="pdm_%s"%s x="%s" y="%s" style="%s"><tspan>%s</tspan></text>'
            % (key, extra, _sh_f(x), _sh_f(y), style, _sh_esc(text)))

    add('<g id="title_block_fields" style="fill:#000000;stroke:none">')
    label("drawn_by", X(1.5), Y(3));        value("drawn_by", X(1.5), Y(8.5))
    label("drawn_date", X(47.5), Y(3));     value("drawn_date", X(47.5), Y(8.5))
    label("approved_by", X(1.5), Y(14));    value("approved_by", X(1.5), Y(19.5))
    label("approved_date", X(47.5), Y(14)); value("approved_date", X(47.5), Y(19.5))
    label("material", X(1.5), Y(25));       value("material", X(1.5), Y(30.5))
    label("scale", X(1.5), Y(36));          value("scale", X(1.5), Y(41.5), text="1:1", autofill="scale")
    label("sheet", X(23.5), Y(36));         value("sheet", X(23.5), Y(41.5), text="1 / 1", autofill="sheet")
    label("mass", X(41.5), Y(36));          value("mass", X(41.5), Y(41.5))
    label("company", X(71.5), Y(3));        value("company", X(71.5), Y(8.8), bold=True)
    label("name", X(71.5), Y(14));          value("name", X(71.5), Y(21.5), size=6, bold=True)
    value("name_translations", X(71.5), Y(26.3), size=2.3)
    label("drawing_number", X(71.5), Y(31)); value("drawing_number", X(71.5), Y(40), size=5, bold=True)
    label("revision", X(141.5), Y(31));     value("revision", X(151), Y(41.5), size=7, bold=True, anchor="middle")
    label("format", X(163.5), Y(31));       value("format", X(171), Y(40.5), text=fmt_name, anchor="middle")
    add("</g>")

    if rec is not None:
        rec["anchors"].update({"logo": (X(163), Y(11), 17.0), "processes": (x0, y0, 180.0), "revisions": (FR, FT, 160.0)})
    add('<g id="pdm_logo" data-x="%s" data-y="%s" data-size="17"/>' % (_sh_f(X(163)), _sh_f(Y(11))))
    add('<g id="pdm_processes" data-x="%s" data-bottom="%s" data-width="180"/>' % (_sh_f(x0), _sh_f(y0)))
    add('<g id="pdm_revisions" data-right="%s" data-top="%s" data-width="160"/>' % (_sh_f(FR), _sh_f(FT)))
    add("</g>")

    return (
        '<?xml version="1.0" encoding="UTF-8" standalone="no"?>\n'
        '<!-- Generated by EasyPDM.FreeCad/templates/build_templates.py; do not edit by hand. -->\n'
        '<svg xmlns="http://www.w3.org/2000/svg" xmlns:xlink="http://www.w3.org/1999/xlink"'
        ' xmlns:freecad="%s" version="1.1"\n'
        '     width="%smm" height="%smm" viewBox="0 0 %s %s">\n'
        '  <title>%s %s landscape</title>\n'
        % (FREECAD_NS, _sh_f(W), _sh_f(H), _sh_f(W), _sh_f(H), SHEET_TITLE_PREFIX, fmt_name)
        + "\n".join("  " + p for p in o) + "\n</svg>\n"
    )


def _processes_table(x0, bottom, width, rows, headers, measure):
    """rows: [{"name", "description", "nameTr": [..], "descTr": [..]}] in the item's order;
    headers: (no, process, description). Header at the bottom, row 1 right above it."""
    w_no, w_name = 10.0, 60.0
    w_desc = width - w_no - w_name
    MAIN, SMALL, LH_MAIN, LH_SMALL, HDR = 3.4, 2.3, 3.6, 2.7, 6.0
    pad = 1.5
    built = []
    for i, r in enumerate(rows):
        name_l = wrap_text(r.get("name", ""), w_name - 2 * pad, MAIN, measure) or [""]
        desc_l = wrap_text(r.get("description", ""), w_desc - 2 * pad, MAIN, measure)
        ntr_l = wrap_joined(r.get("nameTr", []), w_name - 2 * pad, SMALL, measure)
        dtr_l = wrap_joined(r.get("descTr", []), w_desc - 2 * pad, SMALL, measure)
        h = 1.6 + LH_MAIN * max(len(name_l), len(desc_l), 1) + LH_SMALL * max(len(ntr_l), len(dtr_l)) + 0.8
        built.append((i + 1, name_l, desc_l, ntr_l, dtr_l, max(h, 6.0)))
    hdr_top = bottom - HDR
    top = hdr_top - sum(b[5] for b in built)
    o = ['<g style="%s">' % _THIN]
    o.append(_sh_line(x0 + w_no, top, x0 + w_no, bottom))
    o.append(_sh_line(x0 + w_no + w_name, top, x0 + w_no + w_name, bottom))
    o.append(_sh_line(x0, hdr_top, x0 + width, hdr_top))
    yb = hdr_top
    for b in built:
        yt = yb - b[5]
        o.append(_sh_line(x0, yt, x0 + width, yt))
        yb = yt
    o.append('</g><g style="%s">' % _THICK)
    o.append('<rect x="%s" y="%s" width="%s" height="%s"/>' % (_sh_f(x0), _sh_f(top), _sh_f(width), _sh_f(bottom - top)))
    o.append("</g>")
    o.append(_sh_text(x0 + pad, hdr_top + 4.2, headers[0], 2.4, ";font-weight:bold"))
    o.append(_sh_text(x0 + w_no + pad, hdr_top + 4.2, headers[1], 2.4, ";font-weight:bold"))
    o.append(_sh_text(x0 + w_no + w_name + pad, hdr_top + 4.2, headers[2], 2.4, ";font-weight:bold"))
    yb = hdr_top
    for n, name_l, desc_l, ntr_l, dtr_l, h in built:
        yt = yb - h
        o.append(_sh_text(x0 + w_no / 2.0, yt + 5.0, str(n), MAIN, ";text-anchor:middle"))
        for col_x, main_l, small_l in ((x0 + w_no + pad, name_l, ntr_l), (x0 + w_no + w_name + pad, desc_l, dtr_l)):
            y = yt + 4.4
            for line in main_l:
                o.append(_sh_text(col_x, y, line, MAIN))
                y += LH_MAIN
            if not main_l:
                y += LH_MAIN
            y -= 0.6
            for line in small_l:
                o.append(_sh_text(col_x, y, line, SMALL))
                y += LH_SMALL
        yb = yt
    return o


def _revisions_table(right, top, width, rows, headers, measure):
    """rows: [{"label", "date", "description", "by"}] oldest first; headers: (rev, date,
    description, by). Header at the top, rows growing downward."""
    x0 = right - width
    w_rev, w_date, w_by = 12.0, 22.0, 26.0
    w_desc = width - w_rev - w_date - w_by
    SIZE, LH, HDR, pad = 2.6, 3.2, 6.0, 1.5
    o_lines, o_text = [], []
    y = top + HDR
    o_lines.append(_sh_line(x0, y, right, y))
    for r in rows:
        desc_l = wrap_text(r.get("description", ""), w_desc - 2 * pad, SIZE, measure) or [""]
        by_l = wrap_text(r.get("by", ""), w_by - 2 * pad, SIZE, measure) or [""]
        h = max(8.0, 3.0 + LH * max(len(desc_l), len(by_l)))
        o_text.append(_sh_text(x0 + w_rev / 2.0, y + 5.3, r.get("label", ""), 3.4, ";font-weight:bold;text-anchor:middle"))
        o_text.append(_sh_text(x0 + w_rev + pad, y + 5.3, r.get("date", ""), SIZE))
        for i, line in enumerate(desc_l):
            o_text.append(_sh_text(x0 + w_rev + w_date + pad, y + 5.3 + i * LH, line, SIZE))
        for i, line in enumerate(by_l):
            o_text.append(_sh_text(right - w_by + pad, y + 5.3 + i * LH, line, SIZE))
        if r is not rows[-1]:
            o_lines.append(_sh_line(x0, y + h, right, y + h))   # the last one is the frame's edge
        y += h
    bottom = y
    for cx in (x0 + w_rev, x0 + w_rev + w_date, right - w_by):
        o_lines.append(_sh_line(cx, top, cx, bottom))
    o = ['<g style="%s">' % _THIN] + o_lines + ["</g>"]
    o.append('<rect x="%s" y="%s" width="%s" height="%s" style="%s"/>' % (_sh_f(x0), _sh_f(top), _sh_f(width), _sh_f(bottom - top), _THICK))
    hx = (x0 + pad, x0 + w_rev + pad, x0 + w_rev + w_date + pad, right - w_by + pad)
    for x, h in zip(hx, headers):
        o.append(_sh_text(x, top + 4.2, h, 2.4, ";font-weight:bold"))
    return o + o_text


def _group_attrs(svg, gid):
    m = re.search(r'<g\b([^>]*\bid="%s"[^>]*?)\s*/?>' % gid, svg)
    if not m:
        return None
    return dict(re.findall(r'data-([a-z]+)="([^"]*)"', m.group(1)))


def _replace_group(svg, gid, inner):
    """Puts `inner` into the empty or previously filled group `gid`. A filled group ends with
    a </g><!--/gid--> marker, so the old content is found again on the next refresh even
    though it contains nested groups."""
    m = re.search(r'<g\b([^>]*\bid="%s"[^>]*?)\s*/>' % gid, svg)
    if not m:
        m = re.search(r'<g\b([^>]*\bid="%s"[^>]*)>.*?</g><!--/%s-->' % (gid, gid), svg, re.S)
    if not m:
        return svg
    attrs = m.group(1).rstrip()
    new = ('<g%s/>' % attrs) if not inner else ('<g%s>%s</g><!--/%s-->' % (attrs, "".join(inner), gid))
    return svg[:m.start()] + new + svg[m.end():]


def fill_sheet(svg, values, processes=None, revisions=None, process_headers=None,
               revision_headers=None, logo_href=None, measure=None):
    """Writes `values` ({"pdm_name": "Kostka", "pdm_label_name": "NAZWA", ...}) into the
    matching freecad:editable texts and builds the tables and the logo into their groups.
    Works on the EasyPDM template and on any custom template that uses the same names; what
    a template does not have is simply skipped."""
    measure = measure or approx_text_width

    def fill(m):
        name = m.group(2)
        if name not in values:
            return m.group(0)
        return m.group(1) + "<tspan>%s</tspan>" % _sh_esc(values[name]) + m.group(4)

    svg = re.sub(r'(<text\b[^>]*\bfreecad:editable="([^"]+)"[^>]*>)(.*?)(</text>)', fill, svg, flags=re.S)

    a = _group_attrs(svg, "pdm_processes")
    if a is not None:
        inner = []
        if processes:
            inner = _processes_table(float(a.get("x", 0)), float(a.get("bottom", 0)), float(a.get("width", 180)),
                                     processes, process_headers or ("No.", "PROCESS", "DESCRIPTION"), measure)
        svg = _replace_group(svg, "pdm_processes", inner)
    a = _group_attrs(svg, "pdm_revisions")
    if a is not None:
        inner = []
        if revisions:
            inner = _revisions_table(float(a.get("right", 0)), float(a.get("top", 0)), float(a.get("width", 160)),
                                     revisions, revision_headers or ("REV.", "DATE", "DESCRIPTION", "BY"), measure)
        svg = _replace_group(svg, "pdm_revisions", inner)
    a = _group_attrs(svg, "pdm_logo")
    if a is not None:
        inner = []
        if logo_href:
            size, pad = float(a.get("size", 17)), 1.5
            inner = ['<image x="%s" y="%s" width="%s" height="%s" preserveAspectRatio="xMidYMid meet" xlink:href="%s"/>'
                     % (_sh_f(float(a.get("x", 0)) + pad), _sh_f(float(a.get("y", 0)) + pad), _sh_f(size - 2 * pad), _sh_f(size - 2 * pad), logo_href)]
        svg = _replace_group(svg, "pdm_logo", inner)
    return svg

# --- FreeCAD side: refreshing the EasyPDM sheet on a document's TechDraw pages. Uses the
# host macro's api_get / api_get_binary and FreeCAD's App; nothing here runs on import.

def _sh_qt_measure():
    """Text width from the real osifont metrics when Qt is available (inside FreeCAD's GUI),
    so wrapping matches what TechDraw draws; approx_text_width otherwise."""
    try:
        try:
            from PySide6 import QtGui as _QtGui
        except ImportError:
            try:
                from PySide2 import QtGui as _QtGui
            except ImportError:
                from PySide import QtGui as _QtGui
        font_path = os.path.join(App.getResourceDir(), "Mod", "TechDraw", "Resources", "fonts", "osifont-lgpl3fe.ttf")
        families = []
        if os.path.exists(font_path):
            fid = _QtGui.QFontDatabase.addApplicationFont(font_path)
            families = _QtGui.QFontDatabase.applicationFontFamilies(fid) if fid >= 0 else []
        if not families:
            return approx_text_width
        font = _QtGui.QFont(families[0])
        font.setPixelSize(100)
        metrics = _QtGui.QFontMetricsF(font)
        advance = getattr(metrics, "horizontalAdvance", None) or metrics.width
        return lambda text, size: advance(text or "") * size / 100.0
    except Exception:
        return approx_text_width


def _sh_local_date(iso):
    """"2026-11-12T09:14:03.5Z" -> "2026-11-12" in the computer's own time zone."""
    if not iso:
        return ""
    try:
        s = re.sub(r"\.(\d{6})\d+", r".\1", iso.replace("Z", "+00:00"))
        dt = _sh_datetime.fromisoformat(s)
        if dt.tzinfo is not None:
            dt = dt.astimezone()
        return dt.strftime("%Y-%m-%d")
    except Exception:
        return iso[:10]


def _sh_scale_text(scale):
    try:
        s = float(scale)
    except Exception:
        return "1:1"
    if s <= 0:
        return "1:1"
    if s < 1:
        return "1:%s" % ("%g" % round(1.0 / s, 3))
    return "%s:1" % ("%g" % round(s, 3))


def _sh_logo_href(tb):
    company = tb.get("company") or {}
    if not company.get("hasLogo"):
        return None
    try:
        data = api_get_binary("/settings/company/logo")
    except Exception:
        return None
    mime = "image/png" if data[:4] == b"\x89PNG" else "image/jpeg" if data[:2] == b"\xff\xd8" else None
    if not mime:
        return None
    return "data:%s;base64,%s" % (mime, _sh_base64.b64encode(data).decode("ascii"))


def sheet_values(tb, page_scale, sheet_no, sheet_count):
    """Values for the pdm_* fields from GET /items/{id}/title-block."""
    labels = tb.get("labels") or {}
    v = {}
    for field, (key, english) in SHEET_LABELS.items():
        v["pdm_label_" + field] = (labels.get(key) or english).upper()
    drawn = tb.get("drawnBy") or {}
    approved = tb.get("approvedBy") or {}
    company = tb.get("company") or {}
    mass = tb.get("mass")
    v.update({
        "pdm_drawn_by": drawn.get("name") or "",
        "pdm_drawn_date": _sh_local_date(drawn.get("at")),
        "pdm_approved_by": approved.get("name") or "",
        "pdm_approved_date": _sh_local_date(approved.get("at")),
        "pdm_material": tb.get("material") or "",
        "pdm_mass": ("%s kg" % mass) if mass else "",
        "pdm_company": company.get("name") or "",
        "pdm_name": tb.get("name") or "",
        "pdm_name_translations": " \u00b7 ".join(
            "%s: %s" % (x.get("languageCode"), x.get("name")) for x in tb.get("nameTranslations") or []),
        "pdm_drawing_number": tb.get("drawingNumber") or "",
        "pdm_revision": tb.get("revisionLabel") or "",
        "pdm_scale": _sh_scale_text(page_scale),
        "pdm_sheet": "%d / %d" % (sheet_no, sheet_count),
    })
    return v


def sheet_tables(tb):
    labels = tb.get("labels") or {}
    lab = lambda k, d: (labels.get(k) or d).upper()
    processes = []
    for p in tb.get("processes") or []:
        tr = p.get("translations") or []
        processes.append({
            "name": p.get("name") or "",
            "description": p.get("description") or "",
            "nameTr": ["%s: %s" % (x.get("languageCode"), x.get("name")) for x in tr if x.get("name")],
            "descTr": ["%s: %s" % (x.get("languageCode"), x.get("description")) for x in tr if x.get("description")],
        })
    revisions = [{
        "label": r.get("revisionLabel") or "",
        "date": _sh_local_date(r.get("at")),
        "description": r.get("description") or "",
        "by": r.get("by") or "",
    } for r in tb.get("revisions") or []]
    return (processes, revisions,
            (lab("processNo", "No."), lab("process", "Process"), lab("processDescription", "Description")),
            (lab("revisionLetter", "Rev."), lab("revisionDate", "Date"), lab("revisionDescription", "Change description"), lab("revisionBy", "By")))


def is_pdm_template(tpl):
    try:
        return tpl is not None and any(k.startswith("pdm_") for k in dict(tpl.EditableTexts))
    except Exception:
        return False


def _sh_template_text(tpl):
    for path in (getattr(tpl, "Template", ""), getattr(tpl, "PageResult", "")):
        if path and os.path.exists(path):
            with open(path, encoding="utf-8") as f:
                return f.read()
    return ""


def _sh_write_sheet(doc, page, svg):
    """A new file name on every refresh: FreeCAD reloads a template only when the path
    changes. Older working copies of the same page are removed; the .FCStd keeps its own."""
    d = os.path.join(App.getUserAppDataDir(), "EasyPDM", "sheets")
    os.makedirs(d, exist_ok=True)
    prefix = re.sub(r"[^A-Za-z0-9_-]+", "_", "%s_%s" % (doc.Name, page.Name))
    for old in _sh_glob.glob(os.path.join(d, prefix + "_*.svg")):
        try:
            os.remove(old)
        except OSError:
            pass
    path = os.path.join(d, "%s_%d.svg" % (prefix, int(_sh_time.time() * 1000)))
    with open(path, "w", encoding="utf-8", newline="\n") as f:
        f.write(svg)
    return path


def _sh_refresh_page(doc, page, tb, sheet_no, sheet_count, logo_href, measure):
    """Rebuilds one page's sheet; returns False when nothing changed (the template is then
    left alone, so an unchanged document does not turn "modified")."""
    tpl = page.Template
    current = _sh_template_text(tpl) if tpl is not None else ""
    own = (not current) or (SHEET_TITLE_PREFIX in current)
    if own:
        m = re.search(re.escape(SHEET_TITLE_PREFIX) + r" (\w+)", current or "")
        base = build_base_sheet(m.group(1) if m and m.group(1) in SHEET_FORMATS else "A3")
    else:
        base = current
    values = sheet_values(tb, getattr(page, "Scale", 1.0), sheet_no, sheet_count)
    if not own:
        values.pop("pdm_label_format", None)
    processes, revisions, p_head, r_head = sheet_tables(tb)
    svg = fill_sheet(base, values, processes, revisions, p_head, r_head, logo_href, measure)

    old_texts = dict(tpl.EditableTexts) if tpl is not None else {}
    if tpl is not None and svg == current and all(old_texts.get(k) == v for k, v in values.items() if k in old_texts):
        return False
    if tpl is None:
        tpl = doc.addObject("TechDraw::DrawSVGTemplate", "EasyPDMTemplate")
        page.Template = tpl
    tpl.Template = _sh_write_sheet(doc, page, svg)
    texts = dict(tpl.EditableTexts)
    for k, val in old_texts.items():
        if not k.startswith("pdm_") and k in texts:
            texts[k] = val     # fields of a custom template keep what was typed into them
    for k, val in values.items():
        if k in texts:
            texts[k] = val
    tpl.EditableTexts = texts
    return True


def refresh_sheets(doc, item_id, ask_existing_page=None):
    """Fills every TechDraw page of `doc` that uses the EasyPDM sheet (pdm_* fields) with the
    item's title block data. When the document has pages but none with the sheet,
    `ask_existing_page(page)` -- if given -- decides whether the sheet goes on the first of
    them (its views stay). Never creates a page. Returns the pages that changed."""
    pages = [o for o in doc.Objects if o.TypeId == "TechDraw::DrawPage"]
    targets = [p for p in pages if is_pdm_template(p.Template)]
    if not pages or (not targets and ask_existing_page is None):
        return []
    # Data first, changes after: a server without this endpoint (older than 0.8.1) fails
    # here, before an ordinary page has had its template swapped for an empty one.
    tb = api_get("/items/%s/title-block" % item_id)
    if not targets and ask_existing_page(pages[0]):
        old = pages[0].Template
        tpl = doc.addObject("TechDraw::DrawSVGTemplate", "EasyPDMTemplate")
        pages[0].Template = tpl
        if old is not None and not old.InList:
            doc.removeObject(old.Name)
        targets = [pages[0]]
    if not targets:
        return []
    logo = _sh_logo_href(tb)
    measure = _sh_qt_measure()
    changed = [p for p in targets
               if _sh_refresh_page(doc, p, tb, pages.index(p) + 1, len(pages), logo, measure)]
    if changed:
        doc.recompute()
    return changed

# ===== END SHARED =====


def _match_lang(raw):
    raw = (raw or "").strip().lower()
    if not raw:
        return None
    if raw.startswith("pl") or "polish" in raw or "polski" in raw:
        return "pl"
    if raw.startswith("de") or "german" in raw or "deutsch" in raw:
        return "de"
    if raw.startswith("en") or "english" in raw:
        return "en"
    return None


def _detect_language():
    """Auto-wykrycie języka: najpierw własne ustawienie FreeCAD (Preferences -> General ->
    Language) — bywa zapisane jako nazwa ("Polish"/"German") albo jako kod locale
    ("pl"/"pl_PL"/"de_DE" — stąd dopasowanie i po nazwie, i po prefiksie kodu), a jeśli to
    niejednoznaczne (pusty string albo coś spoza pl/en/de), sprawdzamy locale systemu
    operacyjnego ($LANGUAGE/$LC_ALL/$LANG — na Linuksie zwykle "pl_PL.UTF-8"). Fallback na
    angielski, jeśli nic nie pasuje albo odczyt się nie powiedzie."""
    try:
        raw = App.ParamGet("User parameter:BaseApp/Preferences/General").GetString("Language", "")
    except Exception:
        raw = ""
    lang = _match_lang(raw)
    if lang:
        return lang
    raw_os = os.environ.get("LANGUAGE") or os.environ.get("LC_ALL") or os.environ.get("LANG") or ""
    return _match_lang(raw_os) or "en"


LANG = _detect_language()


TRANSLATIONS = {
    "pl": {
        "no_connection": "Brak połączenia z {url}: {reason}",
        "login_failed_no_session": "Logowanie nie powiodło się — serwer nie zwrócił sesji.",
        "pdm_title": "PDM",
        "unnamed_fallback": "bez_nazwy",
        "easypdm_title": "EasyPDM",
        "easypdm_error_title": "EasyPDM — błąd",
        "login_dialog_title": "Logowanie do PDM",
        "api_address_label": "Adres API:",
        "username_label": "Nazwa użytkownika:",
        "password_label": "Hasło:",
        "login_button": "Zaloguj",
        "cancel_button": "Anuluj",
        "login_missing_fields": "Podaj nazwę użytkownika i hasło.",
        "download_folder_dialog_title": "Pobierz z PDM",
        "logged_in_as": "Zalogowano jako: {name}",
        "logout_button": "Wyloguj",
        "account_label": "Konto:",
        "target_dir_label": "Folder docelowy:",
        "choose_download_folder_caption": "Wybierz folder pobierania",
        "indicate_target_folder": "Wskaż folder docelowy.",
        "cannot_use_folder": "Nie można użyć tego folderu: {error}",
        "logged_out_message": "Wylogowano. Kolejne uruchomienie makra poprosi o ponowne zalogowanie.",
        "wait_timeout": "Upłynął czas oczekiwania.",
        "log_cancelled_not_opened": "Anulowano w przeglądarce — pobrane pliki zostały w folderze, dokument nie został otwarty.",
        "wait_ticket_status": "EasyPDM: czekam na wskazanie elementu w przeglądarce...",
        "log_no_attachments_list": "  {label}: nie udało się pobrać listy załączników ({error}).",
        "log_no_cad_files": "  {label}: brak plików CAD do pobrania (element nie ma żadnych załączników).",
        "log_wrong_format": (
            "  {label}: załącznik oznaczony jako plik CAD ma nieoczekiwane rozszerzenie "
            "\"{ext}\" (oczekiwano .FCStd) — pomijam, żeby nie próbować otworzyć niewłaściwego "
            "pliku ({fileName})."
        ),
        "log_already_present": "  {label}: już jest w folderze (aktualna rewizja), pomijam.",
        "log_relinked": "  {file}: przepiąłem odnośniki na pliki w tym folderze ({count}).",
        "log_relink_failed": "  {file}: nie udało się przepiąć odnośników ({error}) — otwórz i popraw ręcznie.",
        "newer_revision_title": "Nowsza rewizja",
        "newer_revision_body": (
            "W folderze jest już {label} w rewizji {rev_list}, a na serwerze aktualna "
            "jest rewizja {wanted}.\n\nPobrać najnowszą wersję?"
        ),
        "log_keeping_local_revision": "  {label}: zostawiam istniejącą lokalną rewizję ({rev_list}).",
        "log_downloading": "  Pobieram {file}...",
        "log_download_error": "  {label}: BŁĄD pobierania {file} ({error}).",
        "log_saved": "  Zapisano: {file}",
        "log_no_children_list": "  {label}: nie udało się pobrać listy składników ({error}).",
        "log_downloading_top": "Pobieram {number} ({name}) do {dir}...",
        "log_opened": "Otwarto: {path}",
        "log_sheet_refreshed": "Tabelka rysunku odświeżona danymi z EasyPDM.",
        "log_open_failed": "Nie udało się otworzyć {path} w FreeCAD: {error}",
        "log_no_main_file": "Nie udało się ustalić pliku głównego do otwarcia.",
        "open_browser_failed": "Nie udało się otworzyć przeglądarki: {error}",
        "fetch_selected_item_failed": "Nie udało się pobrać danych wybranego elementu: {error}",
        "item_no_longer_exists": "Wybrany element już nie istnieje.",
        "download_interrupted": "Pobieranie przerwane nieoczekiwanym błędem:\n\n",
        "log_so_far": "\n\nDotychczasowy log:\n",
    },
    "en": {
        "no_connection": "Could not connect to {url}: {reason}",
        "login_failed_no_session": "Login failed — the server did not return a session.",
        "pdm_title": "PDM",
        "unnamed_fallback": "unnamed",
        "easypdm_title": "EasyPDM",
        "easypdm_error_title": "EasyPDM — Error",
        "login_dialog_title": "Log in to PDM",
        "api_address_label": "API address:",
        "username_label": "Username:",
        "password_label": "Password:",
        "login_button": "Log in",
        "cancel_button": "Cancel",
        "login_missing_fields": "Enter your username and password.",
        "download_folder_dialog_title": "Download from PDM",
        "logged_in_as": "Logged in as: {name}",
        "logout_button": "Log out",
        "account_label": "Account:",
        "target_dir_label": "Target folder:",
        "choose_download_folder_caption": "Choose download folder",
        "indicate_target_folder": "Choose a target folder.",
        "cannot_use_folder": "Cannot use this folder: {error}",
        "logged_out_message": "Logged out. The next time you run the macro, it will ask you to log in again.",
        "wait_timeout": "The waiting time has expired.",
        "log_cancelled_not_opened": "Cancelled in the browser — the files downloaded so far are in the folder; the document was not opened.",
        "wait_ticket_status": "EasyPDM: waiting for an item to be picked in the browser...",
        "log_no_attachments_list": "  {label}: failed to fetch the attachment list ({error}).",
        "log_no_cad_files": "  {label}: no CAD files to download (the item has no attachments).",
        "log_wrong_format": (
            "  {label}: the attachment marked as the CAD file has an unexpected extension "
            "\"{ext}\" (expected .FCStd) — skipping it rather than trying to open the wrong "
            "file ({fileName})."
        ),
        "log_already_present": "  {label}: already in the folder (current revision), skipping.",
        "log_relinked": "  {file}: links repointed to the files in this folder ({count}).",
        "log_relink_failed": "  {file}: could not repoint the links ({error}) — open and fix by hand.",
        "newer_revision_title": "Newer revision",
        "newer_revision_body": (
            "The folder already has {label} in revision {rev_list}, and the current "
            "revision on the server is {wanted}.\n\nDownload the newest version?"
        ),
        "log_keeping_local_revision": "  {label}: keeping the existing local revision ({rev_list}).",
        "log_downloading": "  Downloading {file}...",
        "log_download_error": "  {label}: ERROR downloading {file} ({error}).",
        "log_saved": "  Saved: {file}",
        "log_no_children_list": "  {label}: failed to fetch the list of children ({error}).",
        "log_downloading_top": "Downloading {number} ({name}) to {dir}...",
        "log_opened": "Opened: {path}",
        "log_sheet_refreshed": "Drawing title block refreshed from EasyPDM.",
        "log_open_failed": "Failed to open {path} in FreeCAD: {error}",
        "log_no_main_file": "Failed to determine the main file to open.",
        "open_browser_failed": "Failed to open the browser: {error}",
        "fetch_selected_item_failed": "Failed to fetch the selected item's data: {error}",
        "item_no_longer_exists": "The selected item no longer exists.",
        "download_interrupted": "Download interrupted by an unexpected error:\n\n",
        "log_so_far": "\n\nLog so far:\n",
    },
    "de": {
        "no_connection": "Keine Verbindung zu {url}: {reason}",
        "login_failed_no_session": "Anmeldung fehlgeschlagen — der Server hat keine Sitzung zurückgegeben.",
        "pdm_title": "PDM",
        "unnamed_fallback": "unbenannt",
        "easypdm_title": "EasyPDM",
        "easypdm_error_title": "EasyPDM — Fehler",
        "login_dialog_title": "Anmeldung bei PDM",
        "api_address_label": "API-Adresse:",
        "username_label": "Benutzername:",
        "password_label": "Passwort:",
        "login_button": "Anmelden",
        "cancel_button": "Abbrechen",
        "login_missing_fields": "Geben Sie Benutzername und Passwort ein.",
        "download_folder_dialog_title": "Von PDM herunterladen",
        "logged_in_as": "Angemeldet als: {name}",
        "logout_button": "Abmelden",
        "account_label": "Konto:",
        "target_dir_label": "Zielordner:",
        "choose_download_folder_caption": "Download-Ordner auswählen",
        "indicate_target_folder": "Wählen Sie einen Zielordner.",
        "cannot_use_folder": "Dieser Ordner kann nicht verwendet werden: {error}",
        "logged_out_message": "Abgemeldet. Beim nächsten Ausführen des Makros werden Sie erneut zur Anmeldung aufgefordert.",
        "wait_timeout": "Die Wartezeit ist abgelaufen.",
        "log_cancelled_not_opened": "Im Browser abgebrochen — die bisher heruntergeladenen Dateien liegen im Ordner, das Dokument wurde nicht geöffnet.",
        "wait_ticket_status": "EasyPDM: warte auf die Auswahl eines Elements im Browser...",
        "log_no_attachments_list": "  {label}: Anhangsliste konnte nicht abgerufen werden ({error}).",
        "log_no_cad_files": "  {label}: keine CAD-Dateien zum Herunterladen (das Element hat keine Anhänge).",
        "log_wrong_format": (
            "  {label}: der als CAD-Datei markierte Anhang hat eine unerwartete Erweiterung "
            "\"{ext}\" (erwartet .FCStd) — wird übersprungen, statt die falsche Datei zu "
            "öffnen ({fileName})."
        ),
        "log_already_present": "  {label}: bereits im Ordner vorhanden (aktuelle Revision), wird übersprungen.",
        "log_relinked": "  {file}: Verknüpfungen auf die Dateien in diesem Ordner umgehängt ({count}).",
        "log_relink_failed": "  {file}: Verknüpfungen konnten nicht umgehängt werden ({error}) — bitte von Hand korrigieren.",
        "newer_revision_title": "Neuere Revision",
        "newer_revision_body": (
            "Im Ordner befindet sich bereits {label} in Revision {rev_list}, und die "
            "aktuelle Revision auf dem Server ist {wanted}.\n\nSoll die neueste Version "
            "heruntergeladen werden?"
        ),
        "log_keeping_local_revision": "  {label}: die vorhandene lokale Revision wird beibehalten ({rev_list}).",
        "log_downloading": "  Lade {file} herunter...",
        "log_download_error": "  {label}: FEHLER beim Herunterladen von {file} ({error}).",
        "log_saved": "  Gespeichert: {file}",
        "log_no_children_list": "  {label}: Liste der Unterelemente konnte nicht abgerufen werden ({error}).",
        "log_downloading_top": "Lade {number} ({name}) nach {dir} herunter...",
        "log_opened": "Geöffnet: {path}",
        "log_sheet_refreshed": "Zeichnungsschriftfeld aus EasyPDM aktualisiert.",
        "log_open_failed": "{path} konnte nicht in FreeCAD geöffnet werden: {error}",
        "log_no_main_file": "Die zu öffnende Hauptdatei konnte nicht ermittelt werden.",
        "open_browser_failed": "Der Browser konnte nicht geöffnet werden: {error}",
        "fetch_selected_item_failed": "Die Daten des ausgewählten Elements konnten nicht abgerufen werden: {error}",
        "item_no_longer_exists": "Das ausgewählte Element existiert nicht mehr.",
        "download_interrupted": "Download durch einen unerwarteten Fehler unterbrochen:\n\n",
        "log_so_far": "\n\nBisheriges Protokoll:\n",
    },
}


def t(key, **kwargs):
    text = TRANSLATIONS.get(LANG, TRANSLATIONS["en"]).get(key, TRANSLATIONS["en"].get(key, key))
    return text.format(**kwargs) if kwargs else text


# Ta sama grupa preferencji co EasyPDMUpload.FCMacro — adres API i sesja logowania są
# współdzielone między oboma makrami (zalogowanie się w jednym starcza dla drugiego).
PARAM_GROUP = "User parameter:BaseApp/EasyPDM"
DEFAULT_BASE_URL = "http://localhost:5000/api"
SESSION_COOKIE_NAME = "pdm_session"


class AuthError(RuntimeError):
    """Brak sesji albo sesja wygasła/została unieważniona."""
    pass


def get_base_url():
    return App.ParamGet(PARAM_GROUP).GetString("ApiBaseUrl", DEFAULT_BASE_URL).rstrip("/")


def set_base_url(url):
    App.ParamGet(PARAM_GROUP).SetString("ApiBaseUrl", url.rstrip("/"))


def get_session_token():
    token = App.ParamGet(PARAM_GROUP).GetString("SessionToken", "")
    return token or None


def set_session_token(token):
    App.ParamGet(PARAM_GROUP).SetString("SessionToken", token or "")


def get_saved_username():
    name = App.ParamGet(PARAM_GROUP).GetString("SavedDisplayName", "")
    return name or None


def set_saved_username(name):
    App.ParamGet(PARAM_GROUP).SetString("SavedDisplayName", name or "")


def get_download_folder():
    """Ostatnio użyty folder pobierania — osobna preferencja (nie dotyczy wysyłania),
    ale w tej samej grupie co reszta ustawień EasyPDM."""
    folder = App.ParamGet(PARAM_GROUP).GetString("DownloadFolder", "")
    return folder or None


def set_download_folder(folder):
    App.ParamGet(PARAM_GROUP).SetString("DownloadFolder", folder or "")


def open_in_browser(url):
    """Otwiera adres w przeglądarce tak, żeby wyszła NA WIERZCH.

    Dotąd było to `webbrowser.open`, który uruchamia po prostu `xdg-open`. Pod Wayland nowy
    proces dostaje fokus tylko wtedy, gdy uruchamiający przekaże mu token aktywacji
    (xdg-activation) — a `webbrowser` żadnego nie przekazuje. KDE otwierało więc kartę w tle
    i jedynie podświetlało przeglądarkę na pasku zadań; trzeba było ją wyciągać ręcznie
    (zgłoszone z praktyki, KDE/Wayland).

    `QDesktopServices.openUrl` robi to samo, ale przez Qt, który od wersji 6.6 prosi
    kompozytor o token w imieniu FreeCAD-a i przekazuje go dalej. Token jest ważny, bo
    w tej chwili fokus ma FreeCAD — użytkownik właśnie uruchomił w nim makro.

    `webbrowser.open` zostaje jako zapas: gdy Qt nie ma tej funkcji albo odmówi (stare
    FreeCAD, brak środowiska graficznego), zachowanie jest dokładnie takie jak dotąd."""
    try:
        try:
            from PySide6 import QtGui
        except ImportError:
            try:
                from PySide2 import QtGui
            except ImportError:
                from PySide import QtGui
        if QtGui.QDesktopServices.openUrl(QtCore.QUrl(url)):
            return
    except Exception:
        pass
    webbrowser.open(url)


# Pełny <title> aplikacji (EasyPDM.Web/index.html — musi się z nim zgadzać co do znaku).
# Okno przeglądarki dopasowujemy po POCZĄTKU
# tytułu, bo przeglądarki doklejają swoją nazwę na końcu. NIE po samym "EasyPDM": u autora
# okno Shotcuta miało w tytule "EasyPDM2.mlt", więc takie dopasowanie wyciągnęłoby na
# wierzch montaż wideo zamiast przeglądarki (wyłapane sondą na żywej sesji KDE).
APP_WINDOW_TITLE = "EasyPDM — CAD item browser"

# Skrypt dla KWin. Szuka zwykłego okna, którego tytuł zaczyna się od tytułu aplikacji, i
# aktywuje je. Plasma 6 ma windowList/activeWindow, Plasma 5 clientList/activeClient.
_KWIN_RAISE_SCRIPT = """
const wins = workspace.windowList ? workspace.windowList() : workspace.clientList();
for (const w of wins) {
    if (w.normalWindow && (%(match)s)) {
        if (workspace.activeWindow !== undefined) workspace.activeWindow = w;
        else workspace.activeClient = w;
        break;
    }
}
"""

# Okno FreeCAD-a: najpierw po numerze procesu, a gdy nie pasuje (FreeCAD z Flatpaka ma w
# piaskownicy inny pid niż ten, który widzi KWin) -- po klasie okna.
_KWIN_FREECAD_MATCH = (
    "w.pid === %(pid)d || !wins.some(function (x) { return x.normalWindow && x.pid === %(pid)d; })"
    " && (w.resourceClass || \"\").toLowerCase().indexOf(\"freecad\") >= 0"
)


def _raise_via_kwin(match_js=None):
    """Wyciąga okno przeglądarki na wierzch przez KWin — działa na KDE, także pod Wayland.

    Pod Wayland żadna aplikacja nie może sama aktywować okna innej. Może to jednak zrobić
    kompozytor, a KWin przyjmuje skrypty przez DBus (org.kde.KWin /Scripting) — tak samo
    działa `kdotool`. Skrypt jest zapisywany do pliku tymczasowego, wczytywany, uruchamiany i
    od razu zdejmowany.

    Potrzebne, bo token aktywacji (zob. open_in_browser) pomaga tylko przeglądarce
    URUCHAMIANEJ od zera. Gdy już działa, `xdg-open` startuje jedynie jej krótki proces
    pośredniczący, który przekazuje adres do działającego okna — a czy to okno skorzysta z
    tokenu, zależy od przeglądarki (zgłoszone z praktyki: zamknięta przeglądarka wychodziła na
    wierzch, otwarta — nie).

    `match_js` to warunek JS na oknie `w`; domyślnie okno przeglądarki z EasyPDM (po
    początku tytułu). Ten sam mechanizm wyciąga na wierzch sam FreeCAD -- zob.
    _show_on_top.

    Zwraca True, gdy skrypt udało się uruchomić — nie mówi, czy okno znalazł. Poza KDE (brak
    gdbus albo usługi org.kde.KWin) po prostu zwraca False."""
    if shutil.which("gdbus") is None:
        return False
    plugin = "easypdm-raise-browser"
    path = None

    def call(object_path, method, *args):
        return subprocess.run(
            ["gdbus", "call", "--session", "--dest", "org.kde.KWin",
             "--object-path", object_path, "--method", method, *args],
            capture_output=True, text=True, timeout=3,
        )

    try:
        fd, path = tempfile.mkstemp(prefix="easypdm-kwin-", suffix=".js")
        with os.fdopen(fd, "w", encoding="utf-8") as f:
            # json.dumps daje poprawny literał JS, z polskimi znakami jako \uXXXX.
            if match_js is None:
                match_js = '(w.caption || "").indexOf(%s) === 0' % json.dumps(APP_WINDOW_TITLE)
            f.write(_KWIN_RAISE_SCRIPT % {"match": match_js})
        # Gdyby poprzednie uruchomienie zostawiło skrypt wczytany, loadScript by odmówił.
        call("/Scripting", "org.kde.kwin.Scripting.unloadScript", plugin)
        loaded = call("/Scripting", "org.kde.kwin.Scripting.loadScript", path, plugin)
        found = re.search(r"-?\d+", loaded.stdout or "")
        if loaded.returncode != 0 or not found or int(found.group()) < 0:
            return False
        ran = call(f"/Scripting/Script{found.group()}", "org.kde.kwin.Script.run")
        call("/Scripting", "org.kde.kwin.Scripting.unloadScript", plugin)
        return ran.returncode == 0
    except Exception:
        return False
    finally:
        if path:
            try:
                os.remove(path)
            except OSError:
                pass


def _main_window():
    """Główne okno FreeCAD jako rodzic dla okien makra (None bez GUI)."""
    try:
        import FreeCADGui as Gui

        return Gui.getMainWindow()
    except Exception:
        return None


def _show_on_top(icon, title, text):
    """Komunikat, który wychodzi NA WIERZCH, także spod przeglądarki.

    Okna po wyborze elementu pojawiają się, gdy na wierzchu jest przeglądarka -- to w niej
    właśnie coś kliknięto. Okno bez rodzica lądowało pod nią (i pod samym FreeCAD-em), więc
    podsumowanie pobierania czekało niewidoczne, a nie było wiadomo, czy coś się jeszcze
    dzieje (zgłoszone przez użytkownika, KDE/Wayland). Pod Waylandem FreeCAD sam nie może
    wyjść przed inne okno, więc najpierw prosi o to KWin (jak przy przeglądarce, zob.
    _raise_via_kwin), a okno dostaje FreeCAD za rodzica -- menedżer okien trzyma je wtedy
    nad nim."""
    if sys.platform.startswith("linux"):
        _raise_via_kwin(_KWIN_FREECAD_MATCH % {"pid": os.getpid()})
    box = QtWidgets.QMessageBox(icon, title, text, QtWidgets.QMessageBox.Ok, _main_window())
    box.show()
    box.raise_()
    box.activateWindow()
    box.exec()


def _focus_browser_window():
    """Przenosi okno przeglądarki z EasyPDM na wierzch — odpowiednik `AppActivate "EasyPDM"`
    z makr SolidWorks/Inventor. Kopia (celowo zduplikowana,
    zob. LoginDialog) funkcji z EasyPDMUpload.FCMacro. Tylko dla Linuksa; na Windowsie nie ma tu czego naprawiać.

    Najpierw KWin (KDE, X11 i Wayland — zob. _raise_via_kwin), potem `wmctrl`/`xdotool`
    (inne środowiska pod X11). Poza tym — GNOME pod Wayland — nie zadziała nic, bo kompozytor
    na to nie pozwala; od strony przeglądarki czeka wtedy powiadomienie systemowe, którego
    kliknięcie przełącza na kartę."""
    if _raise_via_kwin():
        return True
    for command in (["wmctrl", "-a", APP_WINDOW_TITLE],
                    ["xdotool", "search", "--name", "^" + re.escape(APP_WINDOW_TITLE), "windowactivate"]):
        if shutil.which(command[0]) is None:
            continue
        try:
            done = subprocess.run(command, timeout=3,
                                  stdout=subprocess.DEVNULL, stderr=subprocess.DEVNULL)
            if done.returncode == 0:
                return True
        except Exception:
            pass
    return False


def build_browser_download_url(ticket):
    """Adres, pod którym otwiera się przeglądarka systemowa zamiast natywnej wyszukiwarki
    Części/Złożenia (zob. wait_for_ticket/main) — most logowania bilet->ciasteczko
    (GET /api/auth/browser-login) plus deep-link "?ticket=&mode=download"
    (pending-create-ticket.ts w aplikacji webowej) — "mode=download" mówi PendingTicketBanner,
    żeby od razu pokazać samą wyszukiwarkę (bez opcji "nowy element", nieistotnej przy
    pobieraniu) i pominąć checkbox STEP (dotyczy tylko wysyłania). Element wskazuje się przez
    POST /create-tickets/{ticket}/attach-existing — ten sam endpoint co przy dogrywaniu pliku
    w EasyPDMUpload.FCMacro, tu użyty do czystego wskazania "co pobrać", bez tworzenia ani
    zmieniania niczego. "ticket" w query stringu /auth/browser-login (bilet logowania,
    jednorazowy, świeżo pobrany z POST /auth/browser-bridge-ticket -- NIGDY sam token sesji,
    żeby ten nie lądował w historii przeglądarki) to inny byt niż "ticket" wewnątrz
    zakodowanego "redirect" (bilet korelacji wyboru elementu, argument tej funkcji). Frontend
    i API dzielą jeden origin, więc "redirect" to zawsze ścieżka względna zaczynająca się od
    "/" — dokładnie to, co GET /auth/browser-login akceptuje."""
    redirect_path = "/?" + urlencode({"ticket": ticket, "mode": "download"})
    login_ticket = api_post_json("/auth/browser-bridge-ticket", {})["ticket"]
    login_params = {"ticket": login_ticket, "redirect": redirect_path}
    return f"{get_base_url()}/auth/browser-login?{urlencode(login_params)}"


def _auth_headers():
    token = get_session_token()
    return {"Cookie": f"{SESSION_COOKIE_NAME}={token}"} if token else {}


def _read_error_body(http_error):
    try:
        return http_error.read().decode("utf-8") or str(http_error)
    except Exception:
        return str(http_error)


def _raise_for_http_error(e):
    if e.code == 401:
        raise AuthError(_read_error_body(e))
    raise RuntimeError(_read_error_body(e))


# ============================================================================
# Postęp pobierania pokazywany w aplikacji webowej jako lista plików odhaczana w trakcie
# (zob. TransferProgressStore.cs / TransferProgressPanel.tsx). Bliźniacze do tych samych
# funkcji w EasyPDMUpload.FCMacro.
#
# CELOWO nie korzysta z api_get: tamto rzuca wyjątkiem przy błędzie HTTP, a raportowanie
# postępu NIE MOŻE przerwać pobierania.
# ============================================================================

def _progress_send(method, path, payload):
    try:
        data = json.dumps(payload).encode("utf-8")
        headers = {"Content-Type": "application/json"}
        headers.update(_auth_headers())
        req = request.Request(get_base_url() + path, data=data, method=method, headers=headers)
        with request.urlopen(req, timeout=10):
            pass
    except Exception:
        pass


def progress_start(kind, entries):
    if not entries:
        return
    _progress_send("PUT", "/progress", {
        "kind": kind,
        "entries": [{"key": k, "label": l} for k, l in entries],
    })


def progress_mark(key, status):
    if key:
        _progress_send("PATCH", "/progress", {"key": key, "status": status})


# Użytkownik kliknął „Anuluj" w panelu postępu — zob. transfer_cancelled. Słownik, nie
# zwykła zmienna, żeby funkcje mogły go zmieniać bez `global`; przypisanie na poziomie modułu
# wykonuje się przy każdym uruchomieniu makra, więc stan nie przechodzi na kolejny bieg.
_CANCEL = {"requested": False}


def transfer_cancelled():
    """Czy użytkownik kliknął „Anuluj" w panelu postępu w przeglądarce.

    Serwer niczego sam nie przerywa — tylko zapisuje prośbę (POST /api/progress/cancel) — więc
    to makro pyta o nią przy każdym odpytaniu o formularz i przed każdym kolejnym plikiem. Plik,
    który akurat leci, zostaje dokończony: przerwanie w połowie zostawiłoby go uszkodzonego.

    Pierwsze „tak" jest zapamiętywane, żeby nie pytać serwera za każdym razem. Każdy błąd
    (brak połączenia, starszy serwer bez tego endpointu) znaczy „nie anulowano" — to wygoda,
    która nie ma prawa zatrzymać przesyłania."""
    if not _CANCEL["requested"]:
        try:
            probe = api_get("/progress/cancelled")
            if probe and probe.get("cancelled") == 1:
                _CANCEL["requested"] = True
                App.Console.PrintMessage(
                    "EasyPDM: anulowano w przegladarce -- zatrzymuje sie przed kolejnym plikiem\n"
                )
        except Exception:
            pass
    return _CANCEL["requested"]


def progress_finish():
    _progress_send("POST", "/progress/finish", {})


def api_get(path):
    req = request.Request(get_base_url() + path, method="GET", headers=_auth_headers())
    try:
        with request.urlopen(req, timeout=15) as resp:
            body = resp.read().decode("utf-8")
            return json.loads(body) if body else None
    except error.HTTPError as e:
        _raise_for_http_error(e)
    except error.URLError as e:
        raise RuntimeError(t("no_connection", url=get_base_url(), reason=e.reason))


def api_get_binary(path):
    """Jak api_get, ale zwraca surowe bajty odpowiedzi — do pobierania zawartości plików
    (załączników), które nie są JSON-em."""
    req = request.Request(get_base_url() + path, method="GET", headers=_auth_headers())
    try:
        with request.urlopen(req, timeout=120) as resp:
            return resp.read()
    except error.HTTPError as e:
        _raise_for_http_error(e)
    except error.URLError as e:
        raise RuntimeError(t("no_connection", url=get_base_url(), reason=e.reason))


def api_post_json(path, payload):
    data = json.dumps(payload).encode("utf-8")
    headers = {"Content-Type": "application/json"}
    headers.update(_auth_headers())
    req = request.Request(get_base_url() + path, data=data, method="POST", headers=headers)
    try:
        with request.urlopen(req, timeout=15) as resp:
            body = resp.read().decode("utf-8")
            return json.loads(body) if body else None
    except error.HTTPError as e:
        _raise_for_http_error(e)
    except error.URLError as e:
        raise RuntimeError(t("no_connection", url=get_base_url(), reason=e.reason))


def api_login(username, password):
    # Logowanie makra (POST /api/auth/macro-login) daje osobny token makra — widoczny i
    # odwoływalny w Ustawienia -> Użytkownicy — zamiast sesji przeglądarki. Odpowiedź ma ten sam
    # kształt co /auth/login, więc reszta działa bez zmian. Serwer sprzed 0.8 nie zna tej ścieżki
    # (404) — wtedy zwykłe logowanie, jak dotąd.
    data = json.dumps({"username": username, "password": password, "client": "FreeCAD Download"}).encode("utf-8")

    def _post_login(path):
        req = request.Request(
            get_base_url() + path, data=data, method="POST",
            headers={"Content-Type": "application/json"},
        )
        with request.urlopen(req, timeout=10) as resp:
            raw = resp.read().decode("utf-8")
            return (json.loads(raw) if raw else {}), resp.headers.get("Set-Cookie", "")

    try:
        try:
            user, set_cookie_header = _post_login("/auth/macro-login")
        except error.HTTPError as e:
            if e.code != 404:
                raise
            user, set_cookie_header = _post_login("/auth/login")
    except error.HTTPError as e:
        raise RuntimeError(_read_error_body(e))
    except error.URLError as e:
        raise RuntimeError(t("no_connection", url=get_base_url(), reason=e.reason))

    # Token najpierw z treści odpowiedzi (pole "sessionToken" — także dla tokenu makra), potem
    # z ciasteczka, jak dotąd.
    token = user.get("sessionToken") or None
    for part in ([] if token else set_cookie_header.split(";")):
        part = part.strip()
        if part.startswith(f"{SESSION_COOKIE_NAME}="):
            token = part[len(SESSION_COOKIE_NAME) + 1:]
            break
    if not token:
        raise RuntimeError(t("login_failed_no_session"))

    set_session_token(token)
    set_saved_username(user.get("displayName") or user.get("username") or username)
    return user


def api_logout():
    token = get_session_token()
    if token:
        req = request.Request(
            get_base_url() + "/auth/logout", method="POST", headers=_auth_headers()
        )
        try:
            request.urlopen(req, timeout=10)
        except Exception:
            pass
    set_session_token(None)
    set_saved_username(None)


def ensure_logged_in():
    if get_session_token():
        try:
            me = api_get("/auth/me")
            # Odświeżamy zapisaną nazwę z /auth/me — bez tego, jeśli token pochodzi z sesji
            # zapisanej wcześniej BEZ przechodzenia przez api_login() w tej instalacji,
            # SavedDisplayName zostawałoby puste na zawsze mimo ważnej sesji — okno
            # pokazywałoby "Zalogowano jako: ?" (dokładnie tak, jak zaobserwowano w praktyce).
            if me:
                set_saved_username(me.get("displayName") or me.get("username"))
            return True
        except AuthError:
            set_session_token(None)
        except Exception:
            return True

    dlg = LoginDialog()
    return dlg.exec() == QtWidgets.QDialog.Accepted


def sanitize_filename(name):
    cleaned = re.sub(r'[\\/:*?"<>|]+', "_", name).strip()
    return cleaned or t("unnamed_fallback")


def revision_label(n):
    """Rewizje jako wielkie litery: 1->A, 2->B, ..., 26->Z, 27->AA... — ta sama konwersja
    co w EasyPDMUpload.FCMacro/api/types.ts (revisionLabel)."""
    n = int(n)
    label = ""
    while n > 0:
        n, remainder = divmod(n - 1, 26)
        label = chr(65 + remainder) + label
    return label or "A"


def _revision_attachment_pattern(item_number, name):
    """Regex dopasowujący własną konwencję nazewnictwa makr PDM: "numer (nazwa).REWIZJA."
    — grupa 1 to litera rewizji. Ta sama nazwa co nada EasyPDMUpload.FCMacro (zob. tam
    _rename_and_upload) — dzięki temu pobieranie i wysyłanie zawsze się zgadzają."""
    # [A-Za-z]*0* przed numerem: nazwa moze miec literowy prefiks rodzaju i zera wiodace
    # (Ustawienia -> Nazewnictwo), a zalaczniki wgrane przed wlaczeniem tych ustawien maja
    # sam numer -- oba warianty musza pasowac, inaczej pobieranie przestaloby widziec
    # wlasne starsze pliki.
    return re.compile(
        rf"^[A-Za-z]*0*{item_number}\s*(?:\({re.escape(sanitize_filename(name))}\))?\.([A-Za-z]+)\.",
        re.IGNORECASE,
    )


def _find_current_attachment(item, attachments):
    """Wybiera załącznik odpowiadający AKTUALNEJ rewizji elementu.

    Preferowana ścieżka: dokładne dopasowanie po item_attachments.revision_number --
    serwer oznacza nim każdy załącznik "cad"/"drawing" numerem rewizji elementu z chwili
    wgrania (migracja 049), więc to jest autorytatywne, bez zgadywania z nazwy pliku.
    Fallback (dla załączników wgranych PRZED istnieniem tej kolumny): dopasowanie po
    konwencji nazw makr PDM. Jeśli i to nie znajdzie nic (np. element dograny ręcznie w
    aplikacji webowej), bierze po prostu najnowiej wgrany załącznik (lista jest posortowana
    rosnąco po dacie) jako najlepsze przybliżenie.

    Rozważane są TYLKO załączniki z rolą "cad" (albo bez roli w ogóle -- starsze/ręcznie
    dograne pliki sprzed wprowadzenia ról, traktowane jako CAD dla wstecznej zgodności).
    Załączniki "step"/"pdf" to osobne eksporty do podglądu, nigdy pliki do otwarcia w CAD
    -- bez tego filtra powyższy fallback "najnowiej wgrany" mógł (i realnie potrafił, po
    dodaniu eksportu PDF, który wgrywa się na końcu) wybrać PDF zamiast właściwego pliku
    CAD, co kończyło się błędem przy próbie otwarcia go jako dokumentu FreeCAD."""
    attachments = [a for a in attachments if a.get("role") in (None, "cad")]
    if not attachments:
        return None

    wanted_revision = item.get("revisionNumber")
    if wanted_revision:
        for a in attachments:
            if a.get("revisionNumber") == wanted_revision:
                return a

    number = item.get("itemNumber")
    name = item.get("fileName", "")
    if number is not None:
        pattern = _revision_attachment_pattern(number, name)
        matches = []
        for a in attachments:
            m = pattern.match(a["fileName"])
            if m:
                matches.append((m.group(1), a))
        if matches:
            # Serwer wysyła gotowe "revisionLabel" obok "revisionNumber" (zob.
            # RevisionLabeling.cs) -- wolimy je od lokalnego przeliczenia, revision_label()
            # zostaje tylko jako fallback dla starszego serwera bez tego pola.
            wanted = (item.get("revisionLabel") or revision_label(item["revisionNumber"])).upper() if item.get("revisionNumber") else None
            for label, a in matches:
                if wanted and label.upper() == wanted:
                    return a
            return matches[-1][1]
    return attachments[-1]


def _local_revision_files(target_dir, item_number, name):
    """Lokalne pliki w target_dir pasujące do konwencji nazw TEGO elementu (dowolna
    rewizja) — do wykrycia "mam już starszą rewizję" (patrz _download_item)."""
    if item_number is None:
        return []
    pattern = _revision_attachment_pattern(item_number, name)
    result = []
    try:
        for fname in os.listdir(target_dir):
            m = pattern.match(fname)
            if m:
                result.append((m.group(1), os.path.join(target_dir, fname)))
    except OSError:
        pass
    return result


def _download_item(item, target_dir, log, downloaded=None):
    """Cienka nakładka na właściwe pobieranie, pilnująca wyłącznie listy postępu.

    Kluczem pozycji jest ID elementu — to samo, które zwrócił serwer w /descendants.
    Nakładka zamiast wstawek w środku, bo _download_item_inner ma pięć punktów wyjścia i
    może rzucić wyjątkiem; tutaj każda z tych ścieżek odhacza pozycję dokładnie raz, a
    nieudane pobranie zostaje na liście oznaczone jako błąd zamiast wisieć jako "w toku"."""
    progress_mark(item["id"], "active")
    try:
        result = _download_item_inner(item, target_dir, log)
        if result and downloaded is not None:
            downloaded.append(result)
    except Exception:
        progress_mark(item["id"], "failed")
        raise
    progress_mark(item["id"], "done" if result else "failed")
    return result


def _download_item_inner(item, target_dir, log):
    """Pobiera aktualny plik CAD Części/Złożenia `item` do target_dir (patrz reguły 3 i 4
    w docstringu modułu). Zwraca ścieżkę do pliku, który finalnie jest/zostaje w folderze
    (świeżo pobrany, już tam był, albo — gdy użytkownik odmówił pobrania nowszej rewizji —
    ta stara, którą i tak ma), albo None, jeśli nic nie udało się ustalić."""
    number = item.get("itemNumber")
    name = item.get("fileName", "")
    label = f"{item.get('itemNumberLabel') or number}({name})"

    try:
        attachments = api_get(f"/items/{item['id']}/attachments") or []
    except Exception as e:
        log(t("log_no_attachments_list", label=label, error=e))
        return None

    current = _find_current_attachment(item, attachments)
    if current is None:
        log(t("log_no_cad_files", label=label))
        return None

    # Dodatkowe zabezpieczenie NIEZALEŻNE od filtrowania po roli w _find_current_attachment
    # -- gdyby jednak trafił się załącznik z rolą "cad" (albo bez roli) o nieoczekiwanym
    # rozszerzeniu (np. ręcznie podmieniony w aplikacji webowej), makro odmawia otwarcia
    # go jako dokumentu FreeCAD zamiast wywalać się z niejasnym błędem natywnym.
    current_ext = os.path.splitext(current["fileName"])[1].lower()
    if current_ext != ".fcstd":
        log(t("log_wrong_format", label=label, ext=current_ext, fileName=current["fileName"]))
        return None

    target_path = os.path.join(target_dir, current["fileName"])

    if os.path.exists(target_path):
        try:
            same_size = os.path.getsize(target_path) == current.get("fileSize")
        except OSError:
            same_size = False
        if same_size:
            log(t("log_already_present", label=label))
            return target_path

    older = [
        (rev, path)
        for rev, path in _local_revision_files(target_dir, number, name)
        if path != target_path
    ]
    if older:
        rev_list = ", ".join(sorted({rev for rev, _ in older}))
        wanted = (item.get("revisionLabel") or revision_label(item["revisionNumber"])) if item.get("revisionNumber") else "?"
        answer = QtWidgets.QMessageBox.question(
            None,
            t("newer_revision_title"),
            t("newer_revision_body", label=label, rev_list=rev_list, wanted=wanted),
            QtWidgets.QMessageBox.Yes | QtWidgets.QMessageBox.No,
        )
        if answer != QtWidgets.QMessageBox.Yes:
            log(t("log_keeping_local_revision", label=label, rev_list=rev_list))
            return older[0][1] if len(older) == 1 else None

    log(t("log_downloading", file=current["fileName"]))
    try:
        content = api_get_binary(f"/attachments/{current['id']}/file")
    except Exception as e:
        log(t("log_download_error", label=label, file=current["fileName"], error=e))
        return None

    os.makedirs(target_dir, exist_ok=True)
    with open(target_path, "wb") as f:
        f.write(content)
    log(t("log_saved", file=current["fileName"]))
    return target_path


def _flatten_xlinks(file_paths, log):
    """Przepina odnośniki App::Link na pliki leżące OBOK, w tym samym folderze.

    Pobieranie kładzie wszystko płasko w jednym folderze, ale złożenie pamięta ścieżkę
    sprzed wysyłki — jeśli komponenty były wtedy w podfolderze, w pliku zostaje
    `<XLink file="test/8(1ddd).A.FCStd" .../>`. FreeCAD rozwiązuje to WZGLĘDEM folderu
    złożenia, czyli szuka w `.../test/test/...` i zgłasza "Link not restored" oraz
    "Link broken!". Zgłoszone z praktyki: pobrane złożenie otwierało się bez komponentów.

    .FCStd to archiwum ZIP, a ścieżki odnośników to atrybut `file` elementów `<XLink>`
    w Document.xml. Obcinamy z nich katalog — i TYLKO wtedy, gdy plik o tej nazwie
    faktycznie leży w tym samym folderze. Dzięki temu odnośnik, którego nie pobraliśmy
    (coś spoza tego drzewa), zostaje nietknięty zamiast zostać wskazany w próżnię.

    Zapis idzie przez plik tymczasowy i dopiero potem podmianę, żeby przerwanie w trakcie
    nie zostawiło uszkodzonego dokumentu. Każdy błąd jest połykany: to naprawa wygody, a nie
    część pobierania — nieudana nie może wywrócić tego, co już się udało ściągnąć."""
    pattern = re.compile(rb'(<XLink\b[^>]*?\bfile=")([^"]+)(")')
    repaired_total = 0

    for path in file_paths:
        if not path or not path.lower().endswith(".fcstd") or not os.path.exists(path):
            continue
        folder = os.path.dirname(path)
        try:
            with zipfile.ZipFile(path, "r") as zf:
                entries = [(i, zf.read(i.filename)) for i in zf.infolist()]
        except Exception as e:
            log(t("log_relink_failed", file=os.path.basename(path), error=e))
            continue

        changed = 0

        def fix(m):
            nonlocal changed
            stored = m.group(2).decode("utf-8", "replace")
            base = os.path.basename(stored.replace("\\", "/"))
            # Już płaski albo nie mamy takiego pliku obok -- nie ruszamy.
            if stored == base or not os.path.exists(os.path.join(folder, base)):
                return m.group(0)
            changed += 1
            return m.group(1) + base.encode("utf-8") + m.group(3)

        new_entries = []
        for info, data in entries:
            if info.filename.lower().endswith(".xml"):
                data = pattern.sub(fix, data)
            new_entries.append((info, data))

        if changed == 0:
            continue

        try:
            tmp = path + ".easypdm-relink"
            with zipfile.ZipFile(tmp, "w", zipfile.ZIP_DEFLATED) as zf:
                for info, data in new_entries:
                    zf.writestr(info.filename, data)
            os.replace(tmp, path)
            repaired_total += changed
            log(t("log_relinked", file=os.path.basename(path), count=changed))
        except Exception as e:
            try:
                os.remove(tmp)
            except Exception:
                pass
            log(t("log_relink_failed", file=os.path.basename(path), error=e))

    return repaired_total


def _download_children_recursive(item, target_dir, log, seen, downloaded=None):
    """Rekurencyjnie pobiera CAŁE drzewo składników Złożenia (bezpośrednie dzieci, potem
    ich dzieci, itd.) do target_dir — patrz punkt 2 w docstringu modułu. `seen` (zbiór ID
    elementów) chroni przed podwójnym pobraniem tego samego, współdzielonego komponentu."""
    try:
        rows = api_get(f"/items/{item['id']}/children") or []
    except Exception as e:
        label = f"{item.get('itemNumberLabel') or item.get('itemNumber')}({item.get('fileName')})"
        log(t("log_no_children_list", label=label, error=e))
        return
    # UWAGA: odpowiedź to lista {"item": {...}, "quantity": ..., "position": ...} — sam
    # element jest ZAGNIEŻDŻONY pod kluczem "item" (ta sama konwencja co childEntries
    # w item-detail-panel.tsx), NIE płaski obiekt jak w GET /api/items.
    for row in rows:
        # Anulowanie z przeglądarki: stop PRZED kolejnym plikiem. Powrót z rekurencji trafia
        # w pętli rodzica znowu tutaj i dostaje zapamiętaną odpowiedź — tak schodzi całość.
        if transfer_cancelled():
            return
        child = row["item"]
        if child["id"] in seen:
            continue
        seen.add(child["id"])
        _download_item(child, target_dir, log, downloaded)
        if child["itemType"] == "assembly":
            _download_children_recursive(child, target_dir, log, seen, downloaded)


class LoginDialog(QtWidgets.QDialog):
    """Identyczne okno logowania co w EasyPDMUpload.FCMacro (współdzielona sesja, ale
    dwa osobne pliki makr — FreeCAD nie ma niezawodnego sposobu importowania jednego
    makra z drugiego, więc kod jest świadomie zduplikowany, nie importowany)."""

    def __init__(self, parent=None):
        super().__init__(parent)
        self.setWindowTitle(t("login_dialog_title"))
        self.setMinimumWidth(360)

        layout = QtWidgets.QVBoxLayout(self)
        form = QtWidgets.QFormLayout()
        layout.addLayout(form)

        self.server_edit = QtWidgets.QLineEdit(get_base_url())
        form.addRow(t("api_address_label"), self.server_edit)

        self.username_edit = QtWidgets.QLineEdit()
        form.addRow(t("username_label"), self.username_edit)

        self.password_edit = QtWidgets.QLineEdit()
        self.password_edit.setEchoMode(QtWidgets.QLineEdit.Password)
        form.addRow(t("password_label"), self.password_edit)

        self.error_label = QtWidgets.QLabel("")
        self.error_label.setStyleSheet("color: #c0392b;")
        self.error_label.setWordWrap(True)
        layout.addWidget(self.error_label)

        buttons = QtWidgets.QDialogButtonBox(
            QtWidgets.QDialogButtonBox.Ok | QtWidgets.QDialogButtonBox.Cancel
        )
        buttons.button(QtWidgets.QDialogButtonBox.Ok).setText(t("login_button"))
        buttons.button(QtWidgets.QDialogButtonBox.Cancel).setText(t("cancel_button"))
        buttons.accepted.connect(self._try_login)
        buttons.rejected.connect(self.reject)
        layout.addWidget(buttons)

    def _try_login(self):
        self.error_label.setText("")
        set_base_url(self.server_edit.text().strip())
        username = self.username_edit.text().strip()
        password = self.password_edit.text()
        if not username or not password:
            self.error_label.setText(t("login_missing_fields"))
            return
        try:
            api_login(username, password)
        except Exception as e:
            self.error_label.setText(str(e))
            return
        self.accept()


class DownloadFolderDialog(QtWidgets.QDialog):
    """Jedyne natywne okno w całym przebiegu main() — pyta o folder docelowy (gdzie mają
    wylądować pobrane pliki) i pokazuje konto/Wyloguj. Wybór KTÓREGO elementu pobrać zapada
    w przeglądarce (zob. build_browser_download_url/main) — folder to jedyna rzecz, której
    przeglądarka nie może sama ustalić (wybór lokalnego miejsca zapisu wymaga natywnego
    okna systemowego)."""

    def __init__(self, parent=None):
        super().__init__(parent)
        self.result_folder = None

        self.setWindowTitle(t("download_folder_dialog_title"))
        self.setMinimumWidth(440)

        outer = QtWidgets.QVBoxLayout(self)
        form = QtWidgets.QFormLayout()
        outer.addLayout(form)

        account_row = QtWidgets.QHBoxLayout()
        self.account_label = QtWidgets.QLabel(t("logged_in_as", name=get_saved_username() or "?"))
        account_row.addWidget(self.account_label)
        logout_btn = QtWidgets.QPushButton(t("logout_button"))
        logout_btn.clicked.connect(self.on_logout)
        account_row.addWidget(logout_btn)
        account_row.addStretch(1)
        form.addRow(t("account_label"), account_row)

        folder_row = QtWidgets.QHBoxLayout()
        self.folder_edit = QtWidgets.QLineEdit(get_download_folder() or "")
        folder_row.addWidget(self.folder_edit)
        browse_btn = QtWidgets.QPushButton("...")
        browse_btn.setMaximumWidth(32)
        browse_btn.clicked.connect(self.on_browse)
        folder_row.addWidget(browse_btn)
        form.addRow(t("target_dir_label"), folder_row)

        self.error_label = QtWidgets.QLabel("")
        self.error_label.setStyleSheet("color: #c0392b;")
        self.error_label.setWordWrap(True)
        outer.addWidget(self.error_label)

        buttons = QtWidgets.QDialogButtonBox(
            QtWidgets.QDialogButtonBox.Ok | QtWidgets.QDialogButtonBox.Cancel
        )
        buttons.accepted.connect(self.on_submit)
        buttons.rejected.connect(self.reject)
        outer.addWidget(buttons)

    def on_logout(self):
        api_logout()
        QtWidgets.QMessageBox.information(
            self, t("pdm_title"), t("logged_out_message")
        )
        self.reject()

    def on_browse(self):
        start = self.folder_edit.text().strip() or os.path.expanduser("~")
        chosen = QtWidgets.QFileDialog.getExistingDirectory(self, t("choose_download_folder_caption"), start)
        if chosen:
            self.folder_edit.setText(chosen)

    def on_submit(self):
        self.error_label.setText("")
        folder = self.folder_edit.text().strip()
        if not folder:
            self.error_label.setText(t("indicate_target_folder"))
            return
        try:
            os.makedirs(folder, exist_ok=True)
        except OSError as e:
            self.error_label.setText(t("cannot_use_folder", error=e))
            return
        set_download_folder(folder)
        self.result_folder = folder
        self.accept()


def wait_for_ticket(ticket, timeout_seconds=600, raise_browser=False):
    """Czeka, aż element zostanie wskazany w przeglądarce — BEZ własnego okna. Odpowiednik
    (celowo zduplikowany, zob. LoginDialog wyżej) funkcji o tej samej nazwie w
    EasyPDMUpload.FCMacro, gdzie stoi też pełne wyjaśnienie.

    W skrócie: okno „Czekam na przeglądarkę" powstawało zaraz po tym, jak przeglądarka
    dostała fokus, i Qt odbierało jej go z powrotem, przez co lista elementów lądowała ZA
    FreeCAD-em. Makra SolidWorks i Inventor nie mają tu żadnego okna — czekają, pisząc na
    pasku stanu, i tak jest teraz również tutaj.

    Zwraca dane biletu albo None, gdy upłynął czas oczekiwania."""
    import time

    status_bar = None
    try:
        import FreeCADGui as Gui

        status_bar = Gui.getMainWindow().statusBar()
        status_bar.showMessage(t("wait_ticket_status"))
    except Exception:
        status_bar = None

    try:
        deadline = time.time() + timeout_seconds
        polls = 0
        while time.time() < deadline:
            try:
                data = api_get(f"/create-tickets/{ticket}")
                if data and data.get("itemId"):
                    return data
            except Exception:
                # Chwilowy błąd sieci nie przerywa czekania — kolejny obieg spróbuje ponownie.
                pass

            # Przeglądarka otwarta przed chwilą przez open_in_browser: gdy już działała, nowa
            # karta mogła wylądować w tle (zob. _raise_via_kwin). Wyciągamy ją przy pierwszych
            # trzech odpytaniach — strona potrzebuje chwili, żeby załadować się i ustawić tytuł,
            # po którym okno jest rozpoznawane. Tylko trzy, żeby nie wyrywać fokusu komuś, kto
            # świadomie wrócił do FreeCAD-a.
            if raise_browser and polls < 3 and sys.platform.startswith("linux"):
                _focus_browser_window()
            polls += 1

            # Interfejs odświeżany dziesięć razy częściej niż odpytywanie serwera, żeby
            # FreeCAD nie stał zamrożony przez cały czas czekania.
            for _ in range(20):
                try:
                    QtWidgets.QApplication.processEvents()
                except Exception:
                    pass
                time.sleep(0.1)

        App.Console.PrintMessage(f"EasyPDM: {t('wait_timeout')}\n")
        return None
    finally:
        if status_bar is not None:
            try:
                status_bar.clearMessage()
            except Exception:
                pass

def _run_download(top_item, target_dir, log):
    """Faktyczne pobieranie + otwarcie, wydzielone z main() wyłącznie po to, żeby dało się
    je owinąć w jeden szeroki try/except (zob. main()) — błąd, którego nie przewidzieliśmy
    (np. nieoczekiwany kształt odpowiedzi API), ma się skończyć CZYTELNYM komunikatem
    z pełnym tracebackiem, a nie cichym zniknięciem makra bez żadnego okna na końcu
    (dokładnie to przydarzyło się w praktyce, zanim doszło to zabezpieczenie — zob. też
    poprawiony _download_children_recursive, gdzie leżała PIERWOTNA przyczyna)."""
    log(t("log_downloading_top", number=top_item["itemNumber"], name=top_item["fileName"], dir=target_dir))

    seen = {top_item["id"]}

    # Lista do panelu postępu. W odróżnieniu od wysyłki makro NIE zna jej z góry —
    # _download_children_recursive schodzi poziom po poziomie i w tym momencie nie wie, ile
    # plików będzie. Dlatego pytamy serwer o całe poddrzewo jednym zapytaniem; deduplikacja
    # po jego stronie odpowiada tej po "seen" tutaj, więc liczby się zgadzają.
    try:
        rows = api_get(f"/items/{top_item['id']}/descendants") or []
        progress_start("download",
                       [(r["id"], r.get("recordName") or r.get("fileName", "")) for r in rows])
    except Exception:
        pass

    downloaded = []
    top_path = _download_item(top_item, target_dir, log, downloaded)
    if top_item["itemType"] == "assembly":
        _download_children_recursive(top_item, target_dir, log, seen, downloaded)

    progress_finish()

    # Odnośniki muszą wskazywać na pliki leżące OBOK — wszystko pobraliśmy do jednego
    # folderu, więc ścieżka z podfolderem sprzed wysyłki rozwiązałaby się w próżnię.
    # Robione PRZED otwarciem dokumentu: po otwarciu FreeCAD ma już zepsute odnośniki
    # wczytane i samo przepisanie pliku na dysku niczego by nie naprawiło.
    _flatten_xlinks(downloaded, log)

    # Anulowane z przeglądarki: pobrane pliki zostają na dysku, ale dokumentu NIE otwieramy —
    # bez reszty komponentów złożenie otworzyłoby się z brakującymi odnośnikami.
    if _CANCEL["requested"]:
        log(t("log_cancelled_not_opened"))
        return

    if top_path and os.path.exists(top_path):
        try:
            opened = App.openDocument(top_path)
            log(t("log_opened", path=top_path))
        except Exception as e:
            opened = None
            log(t("log_open_failed", path=top_path, error=e))
        # The drawing sheet shows what EasyPDM knows now -- e.g. who approved the item after
        # it was released, which the file sent before release cannot carry. Only pages that
        # already use the EasyPDM sheet; nothing is added or asked here, and the file on disk
        # is left as downloaded (the document is just marked modified when the sheet changed).
        if opened is not None:
            try:
                if refresh_sheets(opened, top_item["id"]):
                    log(t("log_sheet_refreshed"))
            except Exception as e:
                App.Console.PrintMessage("EasyPDM: could not refresh the drawing sheet: %s\n" % e)
    else:
        log(t("log_no_main_file"))


def main():
    if not ensure_logged_in():
        return

    # Jedyne natywne okno w całym przebiegu — folder docelowy + konto. KTÓRY element
    # pobrać wybiera się w przeglądarce (zob. build_browser_download_url), nie tutaj.
    folder_dialog = DownloadFolderDialog()
    if folder_dialog.exec() != QtWidgets.QDialog.Accepted:
        return
    target_dir = folder_dialog.result_folder

    ticket = str(uuid.uuid4())
    try:
        url = build_browser_download_url(ticket)
        open_in_browser(url)
    except Exception as e:
        QtWidgets.QMessageBox.critical(None, t("pdm_title"), t("open_browser_failed", error=e))
        return

    ticket_data = wait_for_ticket(ticket, raise_browser=True)
    if ticket_data is None:
        # Upłynął czas oczekiwania — nic do pobrania.
        return

    try:
        top_item = api_get(f"/items/{ticket_data['itemId']}")
    except Exception as e:
        _show_on_top(QtWidgets.QMessageBox.Critical, t("pdm_title"), t("fetch_selected_item_failed", error=e))
        return
    if top_item is None:
        _show_on_top(QtWidgets.QMessageBox.Critical, t("pdm_title"), t("item_no_longer_exists"))
        return

    log_lines = []

    def log(msg):
        log_lines.append(msg)
        App.Console.PrintMessage(msg + "\n")

    try:
        _run_download(top_item, target_dir, log)
    except Exception:
        import traceback

        tb = traceback.format_exc()
        App.Console.PrintError(tb + "\n")
        _show_on_top(
            QtWidgets.QMessageBox.Critical,
            t("easypdm_error_title"),
            t("download_interrupted")
            + tb
            + t("log_so_far")
            + "\n".join(log_lines[-15:]),
        )
        return

    # Po „Anuluj" w przeglądarce bez okna na koniec — raport z biegu jest już w powiadomieniach,
    # tam, gdzie kliknięto. Zapis przebiegu został w Report View.
    if _CANCEL["requested"]:
        return
    _show_on_top(QtWidgets.QMessageBox.Information, t("easypdm_title"), "\n".join(log_lines[-25:]))


if __name__ == "__main__":
    main()
