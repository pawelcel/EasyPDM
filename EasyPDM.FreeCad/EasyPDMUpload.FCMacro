# -*- coding: utf-8 -*-
"""
EasyPDMUpload — makro FreeCAD do wysyłania aktywnego dokumentu do EasyPDM.

Instalacja / uruchomienie:
    Macro -> Macros... -> "Add path to macro path list" -> wskaż ten folder,
    albo po prostu "Execute macro from file" i wybierz ten plik bezpośrednio.
    Nie wymaga instalacji jako workbench.

Co robi (w tej kolejności):
    1. Zapisuje aktywny dokument na dysku (jeśli nie był jeszcze zapisany, prosi o
       wskazanie ścieżki przez natywne okno "Zapisz jako").
    1a. Pyta o FOLDER DOCELOWY dla lokalnych kopii (Save As) wszystkich dokumentów,
        które zostaną wysłane w tej sesji (patrz punkt 3 niżej) — domyślnie podpowiada
        ostatnio użyty (WSPÓLNA preferencja z EasyPDMDownload.FCMacro, DownloadFolder),
        z możliwością zmiany. Pytane RAZ, na samym początku — obejmuje też automatycznie
        wykryte drzewo złożenia (część/pod-złożenia), wysyłane wcześniej niż otwiera się
        główne okno.
    2. Jeśli etykieta dokumentu wygląda jak "numer (nazwa).REWIZJA" i taki element
       faktycznie istnieje w PDM (zob. match_existing_item), pyta WPROST, natywnie: podpiąć
       bieżącą wersję jako nową rewizję TEGO elementu? Zgoda -> dwa kolejne natywne
       pytania Tak/Nie (STEP? PDF?) i koniec, bez przeglądarki. Odmowa (albo brak takiego
       dopasowania) -> otwiera PRZEGLĄDARKĘ SYSTEMOWĄ, już zalogowaną (most token-
       >ciasteczko, zob. "Logowanie" niżej), na pasku
       "oczekuje żądanie z makra CAD" (widoczny na każdym ekranie aplikacji webowej, dopóki
       bilet czeka). Pasek pokazuje JAWNY wybór trzema przyciskami — WYBÓR "nowy element,
       duplikat czy dogranie do istniejącego" zapada tam, nie lokalnie i nie przez
       przypadkowe kliknięcie byle "Dodaj" gdziekolwiek w aplikacji (świadomie NIE dzieje
       się w ten sposób — inaczej jakiekolwiek "Dodaj" kliknięte w międzyczasie, w
       zupełnie niezwiązanym miejscu, mogłoby przez pomyłkę "połknąć" czekający bilet):
       - **"Nowy element"** — otwiera samowystarczalny POPUP (bez potrzeby wcześniejszej
         nawigacji po panelu projektów po lewej) — dopiero W TYM POPUPIE wybiera się projekt,
         opcjonalnie element nadrzędny, typ (Część/Złożenie), wpisuje nazwę, rodzaj
         (dla Części: Wykonywana/Zakupowa/Normalia/Klienta; dla Złożenia: Wykonywane/
         Zakupowe/Klienta — w obu przypadkach wymagany) i zależne od niego pola (Część
         Wykonywana: Materiał; Zakupowa: Producent/Seria-Typ/Podtyp/Numer zamówieniowy
         1 i 2/Masa; Normalia: Materiał/Norma; Klienta: Klient + Nazwa 2 (dopiero po
         wybraniu Klienta). Złożenie
         Zakupowe: Producent/Seria-Typ/Podtyp; Złożenie Klienta: Klient + Nazwa 2; każde
         Złożenie dodatkowo: Masa),
         a także czy eksportować STEP (domyślnie zaznaczone) i/lub PDF (domyślnie
         odznaczone) — dwa checkboksy w tym samym popupie. Bilet
         jest przypięty JAWNIE do tego jednego, konkretnego popupu — żadne INNE "Dodaj" w
         aplikacji (w drzewie projektu, panelu szczegółów) nigdy przypadkiem go nie
         "połknie". "Anuluj" w popupie wraca do wyboru "Nowy element"/"Duplikuj"/"Dograj
         do istniejącego" bez tworzenia niczego.
       - **"Duplikuj"** — najpierw wyszukiwarka wskazuje ŹRÓDŁOWY element (Część/Złożenie)
         z CAŁEJ bazy, potem otwiera TEN SAM popup co "Nowy element", tylko wstępnie
         wypełniony jego właściwościami (rodzaj/materiał/producent/seria-typ/podtyp/
         numery/norma/masa/klient/nazwa2) —
         BEZ kopiowania żadnego pliku. Wszystkie pola dalej można edytować przed zapisem;
         to zwykłe tworzenie nowego elementu, tylko podpowiedziane danymi ze źródła.
       - **"Dograj do istniejącego"** — rozwija wyszukiwarkę Części/Złożenia z
         CAŁEJ bazy (nie tylko bieżącego projektu, bo komponent może być współdzielony)
         razem z tymi samymi checkboksami STEP/PDF. Jeśli etykieta lokalnego dokumentu wygląda jak
         "numer (nazwa).REWIZJA" (bo to samo makro już go tak nazwało po wcześniejszej
         wysyłce), wyszukiwarka od razu podpowiada dopasowany element — tylko podpowiedź,
         wybór zawsze można zmienić.
       Jeden wspólny formularz/pasek w przeglądarce dla WSZYSTKIEGO, więc te reguły nie mogą
       się już rozjechać między makrem a aplikacją webową. Po zdecydowaniu w przeglądarce
       (dowolną z trzech dróg wyżej), makro (okno "Czekam na przeglądarkę", odpytujące co
       ~2s) samo wykrywa zakończenie i kontynuuje — patrz punkt 3 niżej. Anulowanie w
       przeglądarce/oknie oczekiwania albo przekroczenie 10 minut kończy makro komunikatem,
       bez tworzenia/dogrywania żadnego pliku (element mógł już powstać w PDM, jeśli
       zdążono go zapisać w przeglądarce — tylko plik CAD nie zostanie do niego dograny;
       wtedy trzeba uruchomić makro ponownie i wybrać "dograj do istniejącego").
    2a. **JEDYNA decyzja, która świadomie ZOSTAŁA lokalna** — dla dogrywanego elementu ze
        statusem "wydany" (w tym statusie PDM nie pozwala dogrywać plików — sprawdzane też
        po stronie serwera): makro pyta, czy stworzyć nową rewizję (bezpośrednio przed
        faktycznym dograniem pliku, więc to bardziej potwierdzenie operacji na dysku niż
        dane elementu w PDM). Odmowa → nic nie jest zapisywane. Zgoda → status zmienia się
        na "w pracy" (ten sam mechanizm co w aplikacji webowej), co podnosi numer rewizji.
    3. Element w tym momencie już istnieje w PDM (nowy — stworzony przez formularz w
       przeglądarce; już istniejący — wskazany tam samym paskiem, zob. punkt 2). W obu
       przypadkach makro KOPIUJE bieżący plik dokumentu do
       PDM pod nazwą "numer (nazwa).REWIZJA.rozszerzenie"
       — ten sam format numer/nazwa, w jakim PDM wyświetla Części/Złożenia wszędzie indziej
       (zob. itemDisplayLabel w froncie), plus rewizja jako WIELKA LITERA (A, B, C... — ta
       sama konwencja co revisionLabel() we froncie; numer w bazie zostaje liczbą, to czysto
       kwestia formatowania nazwy). LOKALNY dokument jest też zapisywany (Save As) pod TĄ
       SAMĄ nazwą, w tym samym folderze co oryginał — stary plik zostaje na dysku nietknięty,
       ale doc.FileName od teraz wskazuje na nowy. Dzięki temu złożenie linkujące (App::Link)
       do tego dokumentu, zapisywane PO nim w tej samej sesji (a automatycznie wykryte drzewo
       złożenia zawsze zapisuje złożenie jako ostatnie — patrz niżej), zapisze swój odnośnik
       już pod nową nazwą — dokładnie tą, pod jaką EasyPDMDownload.FCMacro później zapisuje
       pobrane pliki, więc odnośniki po pobraniu od razu się zgadzają (bez tego złożenie
       szukałoby oryginalnej, sprzed-wysyłkowej nazwy pliku, potwierdzone w praktyce
       komunikatem FreeCAD "Link broken! ... File: <oryginalna_nazwa>.FCStd"). Plik zawsze
       idzie przez HTTP (POST /api/items/{id}/attachments). PDM ZACHOWUJE kopie poprzednich
       rewizji (np. "67 (nazwa).A.FCStd" zostaje, gdy powstaje rewizja B) — zastępowana jest
       tylko kopia TEJ SAMEJ rewizji (powtórna wysyłka bez zmiany statusu).

Automatyczne wykrywanie złożenia:
    Jeśli aktywny dokument linkuje (App::Link — standardowy sposób budowania złożeń
    w workbenchu Assembly/Assembly4) do INNYCH, zapisanych plików .FCStd, makro PRZED
    otwarciem głównego okna pyta, czy wysłać całe drzewo automatycznie — podsumowanie
    pokazuje przy okazji, do którego DOKŁADNIE elementu PDM trafi każdy już rozpoznany
    komponent (numer + nazwa), nie tylko nazwę pliku, żeby dało się zauważyć nieaktualne
    dopasowanie (zob. match_existing_item) PRZED czymkolwiek. Po zgodzie: schodzi
    rekurencyjnie w głąb (pod-złożenia też mogą linkować dalej) i dla KAŻDEGO jeszcze nie
    wysłanego komponentu przechodzi przez TEN SAM formularz w przeglądarce co główny
    dokument (patrz punkt 2 wyżej) — jedna karta na raz, po kolei, NIGDY kilka naraz
    (ochrona Windows przed "kradzieżą focusu" i tak wyciszyłaby każdą kolejną kartę
    otwartą zaraz po poprzedniej bez świeżej interakcji użytkownika — stąd natywny popup
    "kliknij OK" tuż przed każdym otwarciem, żeby to kliknięcie policzyło się jako ta
    świeża interakcja). Każdy komponent dostaje więc WŁASNY, niezależny wybór projektu/
    typu/nazwy/rodzaju/eksportu STEP i PDF — te same reguły co dla głównego dokumentu,
    tylko każdy w osobnym bilecie. Wysyła wszystko w kolejności LIŚCIE NAJPIERW, na końcu
    główny dokument, budując po drodze cały BOM (z ilością odczytaną z liczby odnośników
    do tego samego pliku — pojedyncze linki i wzorce/tablice linków liczą się razem).
    Nowo utworzony w ten sposób komponent znika z korzenia projektu w aplikacji webowej,
    gdy tylko zostanie podpięty pod swojego prawdziwego rodzica — jego utworzenie jest
    czystym efektem ubocznym kolejności liście-najpierw, nigdy nie miał być niezależnym
    elementem. Komponent uznaje za "już wysłany", jeśli jego etykieta pasuje do formatu
    "numer (nazwa).REWIZJA" (ten sam, który makro samo nadaje po wysyłce) I taki numer
    istnieje w PDM — wtedy tylko podpina go do BOM-u, bez tworzenia duplikatu i bez
    otwierania dla niego przeglądarki. "Nie" na pytanie o wysłanie drzewa wysyła TYLKO
    bieżący dokument, dokładnie jak dotychczas (bez podelementów).

Logowanie:
    EasyPDM.Api wymaga sesji (ciasteczko pdm_session) dla każdego wywołania poza
    POST /api/auth/login — to samo makro więc też się loguje. Przy pierwszym uruchomieniu
    (albo gdy zapisana sesja wygasła/została unieważniona) pojawia się okno logowania
    (nazwa użytkownika + hasło); token sesji trafia do tych samych preferencji FreeCAD co
    adres API (User parameter:BaseApp/EasyPDM), więc kolejne uruchomienia makra (także po
    restarcie FreeCAD) NIE proszą o ponowne logowanie, dopóki sesja jest ważna (30 dni, tak
    samo jak w aplikacji webowej). W oknie "Folder docelowy" (pierwsze okno w każdym
    przebiegu, zob. punkt 1a) widać, kto jest zalogowany, i można się stamtąd wylogować
    (przycisk "Wyloguj") — kolejne uruchomienie makra od razu poprosi o ponowne zalogowanie.
    Ta sama sesja makra jest NIEZBĘDNA nawet dla kroku 2 (cała decyzja nowy/istniejący i
    wszystko z nią związane dzieje się w przeglądarce) — makro samo musi się cały czas
    potrafić uwierzytelnić, żeby (a) odpytać, czy przeglądarka już skończyła (GET
    /create-tickets), i (b) dograć sam plik CAD do wskazanego elementu (to wciąż robi
    makro, nie przeglądarka — nie ma jak temu zapobiec bez utraty automatyzacji zmiany
    nazwy pliku/eksportu STEP/BOM złożenia). Przy okazji: to WŁAŚNIE ta sesja makra jest
    tym, co loguje przeglądarkę
    automatycznie — makro wymienia swoją sesję na jednorazowy bilet
    (POST /api/auth/browser-bridge-ticket), a GET /api/auth/browser-login zamienia ten
    bilet na ciasteczko przeglądarki (zob. AuthEndpoints.cs), więc logowanie w makrze i
    "darmowe" zalogowanie przeglądarki to JEDNA, ta sama operacja, nie dwie osobne.

Ograniczenia (świadomie poza zakresem pierwszej wersji):
    - Krok 2 (punkt wyżej) wymaga, żeby domyślna przeglądarka systemowa umiała otworzyć
      adres serwera PDM (ten sam, co adres API w preferencjach makra) — na typowej
      instalacji (klient i serwer w tej samej sieci) działa to bez dodatkowej konfiguracji.
      Okno oczekiwania w FreeCAD ma limit 10 minut — po przekroczeniu (albo Anuluj) makro
      kończy się komunikatem, bez dogrania pliku; jeśli element zdążył już powstać w
      przeglądarce, trzeba uruchomić makro ponownie i dograć do niego przez pasek
      "oczekujące żądanie z makra".
    - Automatyczne wykrywanie złożenia działa tylko dla odnośników do ZEWNĘTRZNYCH,
      zapisanych plików (App::Link) — nie dla złożeń trzymanych w jednym pliku jako
      kontenery App::Part (te nie mają osobnych plików do wysłania osobno).
    - Rozpoznanie "już wysłanego" komponentu opiera się na etykiecie dokumentu — makro
      samo ją nadaje po wysłaniu i od razu zapisuje (Save As pod nazwą PDM), więc w
      odróżnieniu od wcześniejszej wersji działa też w NOWEJ sesji FreeCAD, o ile otwarty
      zostanie ten (przemianowany) plik, nie stara kopia sprzed wysyłki.
    - Lokalny plik dokumentu jest teraz PRZENOSZONY na nową nazwę (Save As) przy każdej
      wysyłce — stary plik (pod oryginalną nazwą) zostaje na dysku, ale nie jest już
      aktywnie edytowany/otwarty; jeśli ktoś ręcznie wróci do starego pliku i coś w nim
      zmieni, te zmiany NIE trafią automatycznie do PDM (trzeba by je wysłać z powrotem,
      tworząc kolejną rewizję).
    - Adres API zapisywany jest w preferencjach FreeCAD (User parameter:BaseApp/EasyPDM),
      domyślnie http://localhost:5000/api.
"""

import json
import os
import re
import shutil
import subprocess
import sys
import tempfile
import uuid
import webbrowser
from urllib import error, request
from urllib.parse import quote, urlencode

import FreeCAD as App

try:
    from PySide6 import QtCore, QtWidgets
except ImportError:
    try:
        from PySide2 import QtCore, QtWidgets
    except ImportError:
        from PySide import QtCore
        from PySide import QtGui as QtWidgets  # bardzo stare FreeCAD (Qt4)


# ===== BEGIN SHARED (copied into EasyPDMUpload.FCMacro and EasyPDMDownload.FCMacro by templates/build_templates.py; edit it there) =====
import base64 as _sh_base64
import glob as _sh_glob
import time as _sh_time
from datetime import datetime as _sh_datetime
from xml.sax.saxutils import escape as _xml_escape

FREECAD_NS = "https://www.freecad.org/wiki/index.php?title=Svg_Namespace"
SHEET_TITLE_PREFIX = "EasyPDM drawing sheet"
SHEET_FONT = "osifont"  # ISO 3098 lettering shipped with FreeCAD (Mod/TechDraw/Resources/fonts)
ZONE_LETTERS = "ABCDEFGHJKLMNPQRSTUVWXYZ"
# Landscape formats: width, height (mm) and the number of grid reference fields across and
# down, as ISO 5457 sets them. The fields are 50 mm, laid out symmetrically from the centre
# lines, so the outermost ones absorb the remainder (A1: 50.5 mm at the left) instead of
# leaving a sliver next to the frame.
SHEET_FORMATS = {
    "A3": (420, 297, 8, 6),
    "A2": (594, 420, 12, 8),
    "A1": (841, 594, 16, 12),
}

_THIN = "fill:none;stroke:#000000;stroke-width:0.35;stroke-linecap:round;stroke-linejoin:round"
_THICK = "fill:none;stroke:#000000;stroke-width:0.7;stroke-linecap:round;stroke-linejoin:round"

# Field labels in English; the macro overwrites them with the project's main language from
# the server's document labels (Settings -> Language -> Labels in documents, keys
# titleblock.*). Template field name -> server label key.
SHEET_LABELS = {
    "drawn_by": ("drawnBy", "DRAWN BY"),
    "drawn_date": ("date", "DATE"),
    "approved_by": ("approvedBy", "APPROVED BY"),
    "approved_date": ("date", "DATE"),
    "material": ("material", "MATERIAL"),
    "scale": ("scale", "SCALE"),
    "sheet": ("sheet", "SHEET"),
    "mass": ("mass", "MASS"),
    "company": ("company", "COMPANY"),
    "name": ("name", "NAME"),
    "drawing_number": ("drawingNumber", "DRAWING NUMBER"),
    "revision": ("revision", "REVISION"),
    "format": ("format", "FORMAT"),
}


def _sh_f(v):
    return ("%.2f" % v).rstrip("0").rstrip(".")


def _sh_esc(text):
    return _xml_escape(text or "", {'"': "&quot;"})


def approx_text_width(text, size):
    """Width in mm of `text` set in osifont at `size` mm -- a fallback for when Qt cannot
    measure (no GUI). osifont is narrow; 0.58 em per character errs on the wide side, so a
    line wraps a little early rather than running past its cell."""
    return len(text or "") * size * 0.58


def wrap_text(text, width, size, measure):
    """Splits `text` into lines no wider than `width` mm, at spaces; a single word longer
    than the line is left whole rather than cut mid-word."""
    lines = []
    for para in (text or "").splitlines() or [""]:
        line = ""
        for word in para.split(" "):
            candidate = word if not line else line + " " + word
            if line and measure(candidate, size) > width:
                lines.append(line)
                line = word
            else:
                line = candidate
        lines.append(line)
    while lines and lines[-1] == "":
        lines.pop()
    return lines


def wrap_joined(parts, width, size, measure, sep=" · "):
    """Translations as "EN: Cube · DE: Würfel": on one line while they fit, otherwise one
    language per line (each wrapped further if it is still too long)."""
    parts = [p for p in parts if p]
    if not parts:
        return []
    joined = sep.join(parts)
    if measure(joined, size) <= width:
        return [joined]
    lines = []
    for p in parts:
        lines.extend(wrap_text(p, width, size, measure))
    return lines


def _sh_text(x, y, content, size, extra=""):
    return '<text x="%s" y="%s" style="font-size:%spx;fill:#000000%s">%s</text>' % (
        _sh_f(x), _sh_f(y), _sh_f(size), extra, _sh_esc(content))


def _sh_line(x1, y1, x2, y2):
    return '<path d="M %s,%s L %s,%s"/>' % (_sh_f(x1), _sh_f(y1), _sh_f(x2), _sh_f(y2))


def build_base_sheet(fmt_name, rec=None):
    """The bare template for one format: frame, grid reference, title block with empty
    pdm_* fields and the three empty groups.

    `rec`, when given ({"lines": [], "texts": [], "anchors": {}}), also receives every line
    (x1, y1, x2, y2, width) and text (x, baseline_y, text, size, bold, anchor, field) in mm,
    y down from the top edge -- what build_templates.py turns into the SolidWorks macro that
    draws the same sheet format."""
    W, H, fields_x, fields_y = SHEET_FORMATS[fmt_name]
    o = []
    add = o.append

    def ln(x1, y1, x2, y2, width):
        if rec is not None:
            rec["lines"].append((x1, y1, x2, y2, width))
        return _sh_line(x1, y1, x2, y2)

    def box(x, y, w, h, width):
        if rec is not None:
            for seg in ((x, y, x + w, y), (x + w, y, x + w, y + h), (x + w, y + h, x, y + h), (x, y + h, x, y)):
                rec["lines"].append(seg + (width,))

    def txt(x, y, text, size, bold=False, anchor="start", field=None):
        if rec is not None:
            rec["texts"].append((x, y, text, size, bold, anchor, field))
    add('<g id="sheet" style="font-family:%s">' % SHEET_FONT)

    FL, FT, FR, FB = 20, 10, W - 10, H - 10      # drawing frame
    OL, OT, OR, OB = 15, 5, W - 5, H - 5         # outer line of the grid strip
    cx, cy = W / 2.0, H / 2.0
    box(FL, FT, FR - FL, FB - FT, 0.7)
    add('<rect id="drawing_frame" x="%s" y="%s" width="%s" height="%s" style="%s"/>'
        % (FL, FT, _sh_f(FR - FL), _sh_f(FB - FT), _THICK))
    xs = [cx + 50 * k for k in range(-(fields_x // 2 - 1), fields_x // 2)]
    ys = [cy + 50 * k for k in range(-(fields_y // 2 - 1), fields_y // 2)]
    add('<g id="grid_reference" style="%s">' % _THIN)
    box(OL, OT, OR - OL, OB - OT, 0.35)
    add('<rect x="%s" y="%s" width="%s" height="%s"/>' % (OL, OT, _sh_f(OR - OL), _sh_f(OB - OT)))
    for x in xs:
        add(ln(x, OT, x, FT, 0.35))
        add(ln(x, FB, x, OB, 0.35))
    for y in ys:
        add(ln(OL, y, FL, y, 0.35))
        add(ln(FR, y, OR, y, 0.35))
    add("</g>")
    cols, rows = [FL] + xs + [FR], [FT] + ys + [FB]
    add('<g id="grid_reference_markers" style="font-size:3.5px;text-anchor:middle;fill:#000000;stroke:none">')
    for i in range(len(cols) - 1):
        m = (cols[i] + cols[i + 1]) / 2
        for y in (OT + 3.75, FB + 3.75):
            txt(m, y, str(i + 1), 3.5, anchor="middle")
            add('<text x="%s" y="%s">%d</text>' % (_sh_f(m), _sh_f(y), i + 1))
    for i in range(len(rows) - 1):
        m = (rows[i] + rows[i + 1]) / 2 + 1.25
        for x in ((OL + FL) / 2.0, (FR + OR) / 2.0):
            txt(x, m, ZONE_LETTERS[i], 3.5, anchor="middle")
            add('<text x="%s" y="%s">%s</text>' % (_sh_f(x), _sh_f(m), ZONE_LETTERS[i]))
    add("</g>")
    add('<g id="centring_marks" style="%s">' % _THICK)
    add(ln(cx, 0, cx, FT + 5, 0.7))
    add(ln(cx, H, cx, FB - 5, 0.7))
    add(ln(0, cy, FL + 5, cy, 0.7))
    add(ln(W, cy, FR - 5, cy, 0.7))
    add("</g>")

    # Title block 180 x 44 mm in the bottom-right corner.
    x0, y0 = FR - 180, FB - 44
    X = lambda dx: x0 + dx
    Y = lambda dy: y0 + dy
    add('<g id="title_block_lines" style="%s">' % _THIN)
    add(ln(X(70), Y(0), X(70), Y(44), 0.35))
    for dy in (11, 22, 33):
        add(ln(X(0), Y(dy), X(70), Y(dy), 0.35))
    add(ln(X(46), Y(0), X(46), Y(22), 0.35))
    add(ln(X(22), Y(33), X(22), Y(44), 0.35))
    add(ln(X(40), Y(33), X(40), Y(44), 0.35))
    add(ln(X(70), Y(11), X(180), Y(11), 0.35))
    add(ln(X(70), Y(28), X(180), Y(28), 0.35))
    add(ln(X(163), Y(11), X(163), Y(28), 0.35))
    add(ln(X(140), Y(28), X(140), Y(44), 0.35))
    add(ln(X(162), Y(28), X(162), Y(44), 0.35))
    add("</g>")
    box(x0, y0, 180, 44, 0.7)
    add('<rect id="title_block_frame" x="%s" y="%s" width="180" height="44" style="%s"/>'
        % (_sh_f(x0), _sh_f(y0), _THICK))

    def label(key, x, y):
        txt(x, y, SHEET_LABELS[key][1], 2.0, field="pdm_label_" + key)
        add('<text freecad:editable="pdm_label_%s" x="%s" y="%s" style="font-size:2px;fill:#000000">'
            "<tspan>%s</tspan></text>" % (key, _sh_f(x), _sh_f(y), _sh_esc(SHEET_LABELS[key][1])))

    def value(key, x, y, size=3.5, text="", bold=False, anchor="start", autofill=None):
        style = "font-size:%spx;fill:#000000" % _sh_f(size)
        if bold:
            style += ";font-weight:bold"
        if anchor != "start":
            style += ";text-anchor:%s" % anchor
        txt(x, y, text, size, bold, anchor, "pdm_" + key)
        extra = ' freecad:autofill="%s"' % autofill if autofill else ""
        add('<text freecad:editable="pdm_%s"%s x="%s" y="%s" style="%s"><tspan>%s</tspan></text>'
            % (key, extra, _sh_f(x), _sh_f(y), style, _sh_esc(text)))

    add('<g id="title_block_fields" style="fill:#000000;stroke:none">')
    label("drawn_by", X(1.5), Y(3));        value("drawn_by", X(1.5), Y(8.5))
    label("drawn_date", X(47.5), Y(3));     value("drawn_date", X(47.5), Y(8.5))
    label("approved_by", X(1.5), Y(14));    value("approved_by", X(1.5), Y(19.5))
    label("approved_date", X(47.5), Y(14)); value("approved_date", X(47.5), Y(19.5))
    label("material", X(1.5), Y(25));       value("material", X(1.5), Y(30.5))
    label("scale", X(1.5), Y(36));          value("scale", X(1.5), Y(41.5), text="1:1", autofill="scale")
    label("sheet", X(23.5), Y(36));         value("sheet", X(23.5), Y(41.5), text="1 / 1", autofill="sheet")
    label("mass", X(41.5), Y(36));          value("mass", X(41.5), Y(41.5))
    label("company", X(71.5), Y(3));        value("company", X(71.5), Y(8.8), bold=True)
    label("name", X(71.5), Y(14));          value("name", X(71.5), Y(21.5), size=6, bold=True)
    value("name_translations", X(71.5), Y(26.3), size=2.3)
    label("drawing_number", X(71.5), Y(31)); value("drawing_number", X(71.5), Y(40), size=5, bold=True)
    label("revision", X(141.5), Y(31));     value("revision", X(151), Y(41.5), size=7, bold=True, anchor="middle")
    label("format", X(163.5), Y(31));       value("format", X(171), Y(40.5), text=fmt_name, anchor="middle")
    add("</g>")

    if rec is not None:
        rec["anchors"].update({"logo": (X(163), Y(11), 17.0), "processes": (x0, y0, 180.0), "revisions": (FR, FT, 160.0)})
    add('<g id="pdm_logo" data-x="%s" data-y="%s" data-size="17"/>' % (_sh_f(X(163)), _sh_f(Y(11))))
    add('<g id="pdm_processes" data-x="%s" data-bottom="%s" data-width="180"/>' % (_sh_f(x0), _sh_f(y0)))
    add('<g id="pdm_revisions" data-right="%s" data-top="%s" data-width="160"/>' % (_sh_f(FR), _sh_f(FT)))
    add("</g>")

    return (
        '<?xml version="1.0" encoding="UTF-8" standalone="no"?>\n'
        '<!-- Generated by EasyPDM.FreeCad/templates/build_templates.py; do not edit by hand. -->\n'
        '<svg xmlns="http://www.w3.org/2000/svg" xmlns:xlink="http://www.w3.org/1999/xlink"'
        ' xmlns:freecad="%s" version="1.1"\n'
        '     width="%smm" height="%smm" viewBox="0 0 %s %s">\n'
        '  <title>%s %s landscape</title>\n'
        % (FREECAD_NS, _sh_f(W), _sh_f(H), _sh_f(W), _sh_f(H), SHEET_TITLE_PREFIX, fmt_name)
        + "\n".join("  " + p for p in o) + "\n</svg>\n"
    )


def _processes_table(x0, bottom, width, rows, headers, measure):
    """rows: [{"name", "description", "nameTr": [..], "descTr": [..]}] in the item's order;
    headers: (no, process, description). Header at the bottom, row 1 right above it."""
    w_no, w_name = 10.0, 60.0
    w_desc = width - w_no - w_name
    MAIN, SMALL, LH_MAIN, LH_SMALL, HDR = 3.4, 2.3, 3.6, 2.7, 6.0
    pad = 1.5
    built = []
    for i, r in enumerate(rows):
        name_l = wrap_text(r.get("name", ""), w_name - 2 * pad, MAIN, measure) or [""]
        desc_l = wrap_text(r.get("description", ""), w_desc - 2 * pad, MAIN, measure)
        ntr_l = wrap_joined(r.get("nameTr", []), w_name - 2 * pad, SMALL, measure)
        dtr_l = wrap_joined(r.get("descTr", []), w_desc - 2 * pad, SMALL, measure)
        h = 1.6 + LH_MAIN * max(len(name_l), len(desc_l), 1) + LH_SMALL * max(len(ntr_l), len(dtr_l)) + 0.8
        built.append((i + 1, name_l, desc_l, ntr_l, dtr_l, max(h, 6.0)))
    hdr_top = bottom - HDR
    top = hdr_top - sum(b[5] for b in built)
    o = ['<g style="%s">' % _THIN]
    o.append(_sh_line(x0 + w_no, top, x0 + w_no, bottom))
    o.append(_sh_line(x0 + w_no + w_name, top, x0 + w_no + w_name, bottom))
    o.append(_sh_line(x0, hdr_top, x0 + width, hdr_top))
    yb = hdr_top
    for b in built:
        yt = yb - b[5]
        o.append(_sh_line(x0, yt, x0 + width, yt))
        yb = yt
    o.append('</g><g style="%s">' % _THICK)
    o.append('<rect x="%s" y="%s" width="%s" height="%s"/>' % (_sh_f(x0), _sh_f(top), _sh_f(width), _sh_f(bottom - top)))
    o.append("</g>")
    o.append(_sh_text(x0 + pad, hdr_top + 4.2, headers[0], 2.4, ";font-weight:bold"))
    o.append(_sh_text(x0 + w_no + pad, hdr_top + 4.2, headers[1], 2.4, ";font-weight:bold"))
    o.append(_sh_text(x0 + w_no + w_name + pad, hdr_top + 4.2, headers[2], 2.4, ";font-weight:bold"))
    yb = hdr_top
    for n, name_l, desc_l, ntr_l, dtr_l, h in built:
        yt = yb - h
        o.append(_sh_text(x0 + w_no / 2.0, yt + 5.0, str(n), MAIN, ";text-anchor:middle"))
        for col_x, main_l, small_l in ((x0 + w_no + pad, name_l, ntr_l), (x0 + w_no + w_name + pad, desc_l, dtr_l)):
            y = yt + 4.4
            for line in main_l:
                o.append(_sh_text(col_x, y, line, MAIN))
                y += LH_MAIN
            if not main_l:
                y += LH_MAIN
            y -= 0.6
            for line in small_l:
                o.append(_sh_text(col_x, y, line, SMALL))
                y += LH_SMALL
        yb = yt
    return o


def _revisions_table(right, top, width, rows, headers, measure):
    """rows: [{"label", "date", "description", "by"}] oldest first; headers: (rev, date,
    description, by). Header at the top, rows growing downward."""
    x0 = right - width
    w_rev, w_date, w_by = 12.0, 22.0, 26.0
    w_desc = width - w_rev - w_date - w_by
    SIZE, LH, HDR, pad = 2.6, 3.2, 6.0, 1.5
    o_lines, o_text = [], []
    y = top + HDR
    o_lines.append(_sh_line(x0, y, right, y))
    for r in rows:
        desc_l = wrap_text(r.get("description", ""), w_desc - 2 * pad, SIZE, measure) or [""]
        by_l = wrap_text(r.get("by", ""), w_by - 2 * pad, SIZE, measure) or [""]
        h = max(8.0, 3.0 + LH * max(len(desc_l), len(by_l)))
        o_text.append(_sh_text(x0 + w_rev / 2.0, y + 5.3, r.get("label", ""), 3.4, ";font-weight:bold;text-anchor:middle"))
        o_text.append(_sh_text(x0 + w_rev + pad, y + 5.3, r.get("date", ""), SIZE))
        for i, line in enumerate(desc_l):
            o_text.append(_sh_text(x0 + w_rev + w_date + pad, y + 5.3 + i * LH, line, SIZE))
        for i, line in enumerate(by_l):
            o_text.append(_sh_text(right - w_by + pad, y + 5.3 + i * LH, line, SIZE))
        if r is not rows[-1]:
            o_lines.append(_sh_line(x0, y + h, right, y + h))   # the last one is the frame's edge
        y += h
    bottom = y
    for cx in (x0 + w_rev, x0 + w_rev + w_date, right - w_by):
        o_lines.append(_sh_line(cx, top, cx, bottom))
    o = ['<g style="%s">' % _THIN] + o_lines + ["</g>"]
    o.append('<rect x="%s" y="%s" width="%s" height="%s" style="%s"/>' % (_sh_f(x0), _sh_f(top), _sh_f(width), _sh_f(bottom - top), _THICK))
    hx = (x0 + pad, x0 + w_rev + pad, x0 + w_rev + w_date + pad, right - w_by + pad)
    for x, h in zip(hx, headers):
        o.append(_sh_text(x, top + 4.2, h, 2.4, ";font-weight:bold"))
    return o + o_text


def _group_attrs(svg, gid):
    m = re.search(r'<g\b([^>]*\bid="%s"[^>]*?)\s*/?>' % gid, svg)
    if not m:
        return None
    return dict(re.findall(r'data-([a-z]+)="([^"]*)"', m.group(1)))


def _replace_group(svg, gid, inner):
    """Puts `inner` into the empty or previously filled group `gid`. A filled group ends with
    a </g><!--/gid--> marker, so the old content is found again on the next refresh even
    though it contains nested groups."""
    m = re.search(r'<g\b([^>]*\bid="%s"[^>]*?)\s*/>' % gid, svg)
    if not m:
        m = re.search(r'<g\b([^>]*\bid="%s"[^>]*)>.*?</g><!--/%s-->' % (gid, gid), svg, re.S)
    if not m:
        return svg
    attrs = m.group(1).rstrip()
    new = ('<g%s/>' % attrs) if not inner else ('<g%s>%s</g><!--/%s-->' % (attrs, "".join(inner), gid))
    return svg[:m.start()] + new + svg[m.end():]


def fill_sheet(svg, values, processes=None, revisions=None, process_headers=None,
               revision_headers=None, logo_href=None, measure=None):
    """Writes `values` ({"pdm_name": "Kostka", "pdm_label_name": "NAZWA", ...}) into the
    matching freecad:editable texts and builds the tables and the logo into their groups.
    Works on the EasyPDM template and on any custom template that uses the same names; what
    a template does not have is simply skipped."""
    measure = measure or approx_text_width

    def fill(m):
        name = m.group(2)
        if name not in values:
            return m.group(0)
        return m.group(1) + "<tspan>%s</tspan>" % _sh_esc(values[name]) + m.group(4)

    svg = re.sub(r'(<text\b[^>]*\bfreecad:editable="([^"]+)"[^>]*>)(.*?)(</text>)', fill, svg, flags=re.S)

    a = _group_attrs(svg, "pdm_processes")
    if a is not None:
        inner = []
        if processes:
            inner = _processes_table(float(a.get("x", 0)), float(a.get("bottom", 0)), float(a.get("width", 180)),
                                     processes, process_headers or ("No.", "PROCESS", "DESCRIPTION"), measure)
        svg = _replace_group(svg, "pdm_processes", inner)
    a = _group_attrs(svg, "pdm_revisions")
    if a is not None:
        inner = []
        if revisions:
            inner = _revisions_table(float(a.get("right", 0)), float(a.get("top", 0)), float(a.get("width", 160)),
                                     revisions, revision_headers or ("REV.", "DATE", "DESCRIPTION", "BY"), measure)
        svg = _replace_group(svg, "pdm_revisions", inner)
    a = _group_attrs(svg, "pdm_logo")
    if a is not None:
        inner = []
        if logo_href:
            size, pad = float(a.get("size", 17)), 1.5
            inner = ['<image x="%s" y="%s" width="%s" height="%s" preserveAspectRatio="xMidYMid meet" xlink:href="%s"/>'
                     % (_sh_f(float(a.get("x", 0)) + pad), _sh_f(float(a.get("y", 0)) + pad), _sh_f(size - 2 * pad), _sh_f(size - 2 * pad), logo_href)]
        svg = _replace_group(svg, "pdm_logo", inner)
    return svg

# --- FreeCAD side: refreshing the EasyPDM sheet on a document's TechDraw pages. Uses the
# host macro's api_get / api_get_binary and FreeCAD's App; nothing here runs on import.

def _sh_qt_measure():
    """Text width from the real osifont metrics when Qt is available (inside FreeCAD's GUI),
    so wrapping matches what TechDraw draws; approx_text_width otherwise."""
    try:
        try:
            from PySide6 import QtGui as _QtGui
        except ImportError:
            try:
                from PySide2 import QtGui as _QtGui
            except ImportError:
                from PySide import QtGui as _QtGui
        font_path = os.path.join(App.getResourceDir(), "Mod", "TechDraw", "Resources", "fonts", "osifont-lgpl3fe.ttf")
        families = []
        if os.path.exists(font_path):
            fid = _QtGui.QFontDatabase.addApplicationFont(font_path)
            families = _QtGui.QFontDatabase.applicationFontFamilies(fid) if fid >= 0 else []
        if not families:
            return approx_text_width
        font = _QtGui.QFont(families[0])
        font.setPixelSize(100)
        metrics = _QtGui.QFontMetricsF(font)
        advance = getattr(metrics, "horizontalAdvance", None) or metrics.width
        return lambda text, size: advance(text or "") * size / 100.0
    except Exception:
        return approx_text_width


def _sh_local_date(iso):
    """"2026-11-12T09:14:03.5Z" -> "2026-11-12" in the computer's own time zone."""
    if not iso:
        return ""
    try:
        s = re.sub(r"\.(\d{6})\d+", r".\1", iso.replace("Z", "+00:00"))
        dt = _sh_datetime.fromisoformat(s)
        if dt.tzinfo is not None:
            dt = dt.astimezone()
        return dt.strftime("%Y-%m-%d")
    except Exception:
        return iso[:10]


def _sh_scale_text(scale):
    try:
        s = float(scale)
    except Exception:
        return "1:1"
    if s <= 0:
        return "1:1"
    if s < 1:
        return "1:%s" % ("%g" % round(1.0 / s, 3))
    return "%s:1" % ("%g" % round(s, 3))


def _sh_logo_href(tb):
    company = tb.get("company") or {}
    if not company.get("hasLogo"):
        return None
    try:
        data = api_get_binary("/settings/company/logo")
    except Exception:
        return None
    mime = "image/png" if data[:4] == b"\x89PNG" else "image/jpeg" if data[:2] == b"\xff\xd8" else None
    if not mime:
        return None
    return "data:%s;base64,%s" % (mime, _sh_base64.b64encode(data).decode("ascii"))


def sheet_values(tb, page_scale, sheet_no, sheet_count):
    """Values for the pdm_* fields from GET /items/{id}/title-block."""
    labels = tb.get("labels") or {}
    v = {}
    for field, (key, english) in SHEET_LABELS.items():
        v["pdm_label_" + field] = (labels.get(key) or english).upper()
    drawn = tb.get("drawnBy") or {}
    approved = tb.get("approvedBy") or {}
    company = tb.get("company") or {}
    mass = tb.get("mass")
    v.update({
        "pdm_drawn_by": drawn.get("name") or "",
        "pdm_drawn_date": _sh_local_date(drawn.get("at")),
        "pdm_approved_by": approved.get("name") or "",
        "pdm_approved_date": _sh_local_date(approved.get("at")),
        "pdm_material": tb.get("material") or "",
        "pdm_mass": ("%s kg" % mass) if mass else "",
        "pdm_company": company.get("name") or "",
        "pdm_name": tb.get("name") or "",
        "pdm_name_translations": " \u00b7 ".join(
            "%s: %s" % (x.get("languageCode"), x.get("name")) for x in tb.get("nameTranslations") or []),
        "pdm_drawing_number": tb.get("drawingNumber") or "",
        "pdm_revision": tb.get("revisionLabel") or "",
        "pdm_scale": _sh_scale_text(page_scale),
        "pdm_sheet": "%d / %d" % (sheet_no, sheet_count),
    })
    return v


def sheet_tables(tb):
    labels = tb.get("labels") or {}
    lab = lambda k, d: (labels.get(k) or d).upper()
    processes = []
    for p in tb.get("processes") or []:
        tr = p.get("translations") or []
        processes.append({
            "name": p.get("name") or "",
            "description": p.get("description") or "",
            "nameTr": ["%s: %s" % (x.get("languageCode"), x.get("name")) for x in tr if x.get("name")],
            "descTr": ["%s: %s" % (x.get("languageCode"), x.get("description")) for x in tr if x.get("description")],
        })
    revisions = [{
        "label": r.get("revisionLabel") or "",
        "date": _sh_local_date(r.get("at")),
        "description": r.get("description") or "",
        "by": r.get("by") or "",
    } for r in tb.get("revisions") or []]
    return (processes, revisions,
            (lab("processNo", "No."), lab("process", "Process"), lab("processDescription", "Description")),
            (lab("revisionLetter", "Rev."), lab("revisionDate", "Date"), lab("revisionDescription", "Change description"), lab("revisionBy", "By")))


def is_pdm_template(tpl):
    try:
        return tpl is not None and any(k.startswith("pdm_") for k in dict(tpl.EditableTexts))
    except Exception:
        return False


def _sh_template_text(tpl):
    for path in (getattr(tpl, "Template", ""), getattr(tpl, "PageResult", "")):
        if path and os.path.exists(path):
            with open(path, encoding="utf-8") as f:
                return f.read()
    return ""


def _sh_write_sheet(doc, page, svg):
    """A new file name on every refresh: FreeCAD reloads a template only when the path
    changes. Older working copies of the same page are removed; the .FCStd keeps its own."""
    d = os.path.join(App.getUserAppDataDir(), "EasyPDM", "sheets")
    os.makedirs(d, exist_ok=True)
    prefix = re.sub(r"[^A-Za-z0-9_-]+", "_", "%s_%s" % (doc.Name, page.Name))
    for old in _sh_glob.glob(os.path.join(d, prefix + "_*.svg")):
        try:
            os.remove(old)
        except OSError:
            pass
    path = os.path.join(d, "%s_%d.svg" % (prefix, int(_sh_time.time() * 1000)))
    with open(path, "w", encoding="utf-8", newline="\n") as f:
        f.write(svg)
    return path


def _sh_refresh_page(doc, page, tb, sheet_no, sheet_count, logo_href, measure):
    """Rebuilds one page's sheet; returns False when nothing changed (the template is then
    left alone, so an unchanged document does not turn "modified")."""
    tpl = page.Template
    current = _sh_template_text(tpl) if tpl is not None else ""
    own = (not current) or (SHEET_TITLE_PREFIX in current)
    if own:
        m = re.search(re.escape(SHEET_TITLE_PREFIX) + r" (\w+)", current or "")
        base = build_base_sheet(m.group(1) if m and m.group(1) in SHEET_FORMATS else "A3")
    else:
        base = current
    values = sheet_values(tb, getattr(page, "Scale", 1.0), sheet_no, sheet_count)
    if not own:
        values.pop("pdm_label_format", None)
    processes, revisions, p_head, r_head = sheet_tables(tb)
    svg = fill_sheet(base, values, processes, revisions, p_head, r_head, logo_href, measure)

    old_texts = dict(tpl.EditableTexts) if tpl is not None else {}
    if tpl is not None and svg == current and all(old_texts.get(k) == v for k, v in values.items() if k in old_texts):
        return False
    if tpl is None:
        tpl = doc.addObject("TechDraw::DrawSVGTemplate", "EasyPDMTemplate")
        page.Template = tpl
    tpl.Template = _sh_write_sheet(doc, page, svg)
    texts = dict(tpl.EditableTexts)
    for k, val in old_texts.items():
        if not k.startswith("pdm_") and k in texts:
            texts[k] = val     # fields of a custom template keep what was typed into them
    for k, val in values.items():
        if k in texts:
            texts[k] = val
    tpl.EditableTexts = texts
    return True


def refresh_sheets(doc, item_id, ask_existing_page=None):
    """Fills every TechDraw page of `doc` that uses the EasyPDM sheet (pdm_* fields) with the
    item's title block data. When the document has pages but none with the sheet,
    `ask_existing_page(page)` -- if given -- decides whether the sheet goes on the first of
    them (its views stay). Never creates a page. Returns the pages that changed."""
    pages = [o for o in doc.Objects if o.TypeId == "TechDraw::DrawPage"]
    targets = [p for p in pages if is_pdm_template(p.Template)]
    if not pages or (not targets and ask_existing_page is None):
        return []
    # Data first, changes after: a server without this endpoint (older than 0.8.1) fails
    # here, before an ordinary page has had its template swapped for an empty one.
    tb = api_get("/items/%s/title-block" % item_id)
    if not targets and ask_existing_page(pages[0]):
        old = pages[0].Template
        tpl = doc.addObject("TechDraw::DrawSVGTemplate", "EasyPDMTemplate")
        pages[0].Template = tpl
        if old is not None and not old.InList:
            doc.removeObject(old.Name)
        targets = [pages[0]]
    if not targets:
        return []
    logo = _sh_logo_href(tb)
    measure = _sh_qt_measure()
    changed = [p for p in targets
               if _sh_refresh_page(doc, p, tb, pages.index(p) + 1, len(pages), logo, measure)]
    if changed:
        doc.recompute()
    return changed

# ===== END SHARED =====


def _match_lang(raw):
    raw = (raw or "").strip().lower()
    if not raw:
        return None
    if raw.startswith("pl") or "polish" in raw or "polski" in raw:
        return "pl"
    if raw.startswith("de") or "german" in raw or "deutsch" in raw:
        return "de"
    if raw.startswith("en") or "english" in raw:
        return "en"
    return None


def _detect_language():
    """Auto-wykrycie języka: najpierw własne ustawienie FreeCAD (Preferences -> General ->
    Language) — bywa zapisane jako nazwa ("Polish"/"German") albo jako kod locale
    ("pl"/"pl_PL"/"de_DE" — stąd dopasowanie i po nazwie, i po prefiksie kodu), a jeśli to
    niejednoznaczne (pusty string albo coś spoza pl/en/de), sprawdzamy locale systemu
    operacyjnego ($LANGUAGE/$LC_ALL/$LANG — na Linuksie zwykle "pl_PL.UTF-8"). Fallback na
    angielski, jeśli nic nie pasuje albo odczyt się nie powiedzie."""
    try:
        raw = App.ParamGet("User parameter:BaseApp/Preferences/General").GetString("Language", "")
    except Exception:
        raw = ""
    lang = _match_lang(raw)
    if lang:
        return lang
    raw_os = os.environ.get("LANGUAGE") or os.environ.get("LC_ALL") or os.environ.get("LANG") or ""
    return _match_lang(raw_os) or "en"


LANG = _detect_language()


TRANSLATIONS = {
    "pl": {
        "no_connection": "Brak połączenia z {url}: {reason}",
        "login_failed_no_session": "Logowanie nie powiodło się — serwer nie zwrócił sesji.",
        "pdm_title": "PDM",
        "unnamed_fallback": "bez_nazwy",
        "login_dialog_title": "Logowanie do PDM",
        "api_address_label": "Adres API:",
        "username_label": "Nazwa użytkownika:",
        "password_label": "Hasło:",
        "login_button": "Zaloguj",
        "cancel_button": "Anuluj",
        "assembly_update_note": "Pliki już będące w PDM w statusie \"W pracy\" zostaną zaktualizowane (plik CAD zastąpi tę samą rewizję).",
        "update_step_checkbox": "Wyślij na nowo STEP (podgląd 3D) plików już będących w PDM",
        "update_pdf_checkbox": "Wyślij na nowo PDF plików już będących w PDM",
        "not_sent_suffix": " — {status}, nie zostanie wysłany",
        "locked_not_sent": "Tych plików nie wyślemy — są w PDM ze statusem, który blokuje zmiany. Żeby je zaktualizować, utwórz nową rewizję albo zdejmij je ze sprawdzania:\n\n{lines}",
        "yes_button": "Tak",
        "no_button": "Nie",
        "login_missing_fields": "Podaj nazwę użytkownika i hasło.",
        "sheet_ask_existing_page": "Dokument ma stronę rysunku „{page}” bez arkusza EasyPDM.\n\nWstawić na nią arkusz EasyPDM z tabelką wypełnianą z PDM? Widoki zostają.",
        "target_folder_dialog_title": "Wyślij do PDM",
        "logged_in_as": "Zalogowano jako: {name}",
        "logout_button": "Wyloguj",
        "account_label": "Konto:",
        "target_folder_hint": (
            "Gdzie mają trafić lokalne kopie wysyłanych dokumentów (ten sam plik pod "
            "nazwą PDM, zamiast oryginalnej)? To samo miejsce co folder pobierania w "
            "EasyPDMDownload.FCMacro — warto ustawić jednakowo."
        ),
        "choose_target_folder_caption": "Wybierz folder docelowy",
        "indicate_folder": "Wskaż folder.",
        "cannot_use_folder": "Nie można użyć tego folderu: {error}",
        "logged_out_message": "Wylogowano. Kolejne uruchomienie makra poprosi o ponowne zalogowanie.",
        "new_revision_title": "Nowa rewizja",
        "new_revision_body": (
            'Ten element ma status "Wydany" — nie można do niego dogrywać plików.\n\n'
            'Czy chcesz stworzyć nową rewizję (status zmieni się na "W pracy")?'
        ),
        "revision_comment_label": "Komentarz do rewizji (opcjonalnie):",
        "revision_comment_placeholder": "Co zmieniło się w tej rewizji…",
        "create_revision_button": "Stwórz rewizję",
        "assembly_detected_title": "Wykryto złożenie",
        "assembly_detected_body": (
            "Ten dokument linkuje do {count} innych plików (części/pod-złożeń):\n\n"
            "{summary}\n\n"
            "Wysłać je automatycznie razem z tym dokumentem (najpierw części/pod-złożenia, "
            "na końcu ten dokument)?\n\n"
            "\"Nie\" wyśle TYLKO ten dokument, tak jak dotychczas — bez podelementów."
        ),
        "already_in_pdm_as": " -> JUŻ w PDM jako #{number} ({name})",
        "already_linked_confirm": (
            "Ten dokument wygląda jak już wcześniej wysłany element PDM nr {number} "
            "({name}). Podpiąć bieżącą wersję jako nową rewizję/aktualizację TEGO "
            "elementu?\n\n\"Nie\" otworzy zwykły formularz w przeglądarce (Nowy element / "
            "Duplikuj / Dogranie do istniejącego)."
        ),
        "export_step_prompt": "Wyeksportować i wysłać model STEP (podgląd 3D)?",
        "export_pdf_prompt": "Wyeksportować i wysłać plik PDF?",
        "new_component_browser_prompt": (
            "Nowy element w drzewie: {name}. Kliknij OK, aby otworzyć przeglądarkę i go "
            "wprowadzić (może otworzyć się w tle — sprawdź pasek zadań)."
        ),
        "fetch_items_failed": "Nie udało się pobrać listy elementów: {error}",
        "fetch_projects_failed": "Nie udało się pobrać listy projektów: {error}",
        "upload_component_failed": "Nie udało się wysłać {file}: {error}",
        "link_child_failed": "Utworzono {child}, ale nie udało się podpiąć go pod {parent}: {error}",
        "open_browser_failed": "Nie udało się otworzyć przeglądarki: {error}",
        "wait_timeout": "Upłynął czas oczekiwania.",
        "wait_ticket_status": "EasyPDM: czekam na dane elementu uzupełniane w przeglądarce...",
        "no_active_document": "Brak otwartego dokumentu.",
        "document_not_saved": "Dokument nie jest jeszcze zapisany — wskaż, gdzie go zapisać.",
        "save_failed": "Nie udało się zapisać dokumentu: {error}",
        "final_save_failed": (
            "Tych plików nie udało się zapisać lokalnie. Odwołania do nowych nazw są tylko "
            "w otwartym dokumencie — zapisz je ręcznie (Ctrl+S):\n{lines}"
        ),
        "cancelled_upload": "Przerwano — anulowano wysyłkę.",
        "nothing_sent": "Anulowano — nic nie zostało wysłane.",
        "link_subitem_failed": "Nie udało się podpiąć jednego z podelementów pod główny element: {error}",
        "local_renamed_line": (
            "Lokalny plik zapisany pod nazwą PDM (Save As), stary plik pod oryginalną "
            "nazwą pozostał nietknięty:\n{path}"
        ),
        "local_already_named_line": (
            "Lokalny plik już był pod właściwą nazwą PDM — nic nie trzeba było przenosić:\n{path}"
        ),
        "status_revision_mismatch": (
            "Status/rewizja elementu #{number} zostały już zmienione na "
            "serwerze (rewizja {revision}, status 'w_pracy'), ale dogranie pliku się nie "
            "powiodło: {error}\n\nElement w PDM ma teraz nową rewizję, lecz wciąż plik "
            "poprzedniej wersji — popraw to ręcznie w aplikacji webowej (dograj plik "
            "ponownie) albo spróbuj ponownie z tego makra."
        ),
        "upload_blocked_review": (
            "Nie można wysłać — element #{number} ma status \"Sprawdzany\". Poczekaj, aż "
            "recenzja się zakończy (element wróci do statusu \"W pracy\"), albo zmień "
            "status ręcznie w aplikacji webowej."
        ),
        "status_label_sprawdzany": "Sprawdzany",
        "status_label_wydany": "Wydany",
        "locked_components_tail": (
            "\n\nUwaga: {count} już podlinkowany(-e) komponent(y) w złożeniu ma "
            "zablokowany status — NIE zostały zaktualizowane (drzewo złożenia nigdy nie "
            "dosyła ponownie już-istniejących komponentów, ale te akurat są dodatkowo "
            "zablokowane statusem, więc gdybyś je zmieniał lokalnie, wyślij je osobno po "
            "cofnięciu statusu do \"W pracy\"):\n{lines}"
        ),
        "stale_children_confirm": (
            "{count} podelement(ów) tego elementu istnieje w PDM, ale nie ma ich już w "
            "lokalnej strukturze złożenia (usunięte z drzewa FreeCAD od poprzedniej "
            "wysyłki):\n{lines}\n\nUsunąć te powiązania z PDM? (Same elementy NIE zostaną "
            "skasowane, tylko ich podpięcie pod to złożenie.)"
        ),
    },
    "en": {
        "no_connection": "Could not connect to {url}: {reason}",
        "login_failed_no_session": "Login failed — the server did not return a session.",
        "pdm_title": "PDM",
        "unnamed_fallback": "unnamed",
        "login_dialog_title": "Log in to PDM",
        "api_address_label": "API address:",
        "username_label": "Username:",
        "password_label": "Password:",
        "login_button": "Log in",
        "cancel_button": "Cancel",
        "assembly_update_note": "Files already in the PDM with status \"In work\" will be updated (their CAD file replaces the same revision).",
        "update_step_checkbox": "Upload a fresh STEP (3D preview) for files already in the PDM",
        "update_pdf_checkbox": "Upload a fresh PDF for files already in the PDM",
        "not_sent_suffix": " — {status}, will not be sent",
        "locked_not_sent": "These files will not be sent — they are in the PDM with a status that blocks changes. To update them, create a new revision or take them out of review:\n\n{lines}",
        "yes_button": "Yes",
        "no_button": "No",
        "login_missing_fields": "Enter your username and password.",
        "sheet_ask_existing_page": "The document has the drawing page \"{page}\" without the EasyPDM sheet.\n\nPut the EasyPDM sheet on it, with the title block filled in from PDM? Its views stay.",
        "target_folder_dialog_title": "Send to PDM",
        "logged_in_as": "Logged in as: {name}",
        "logout_button": "Log out",
        "account_label": "Account:",
        "target_folder_hint": (
            "Where should local copies of uploaded documents go (the same file under the "
            "PDM name, instead of the original)? This is the same location as the download "
            "folder in EasyPDMDownload.FCMacro — it's a good idea to set them the same."
        ),
        "choose_target_folder_caption": "Choose target folder",
        "indicate_folder": "Choose a folder.",
        "cannot_use_folder": "Cannot use this folder: {error}",
        "logged_out_message": "Logged out. The next time you run the macro, it will ask you to log in again.",
        "new_revision_title": "New revision",
        "new_revision_body": (
            'This item has the status "Released" — files cannot be added to it.\n\n'
            'Do you want to create a new revision (the status will change to "In progress")?'
        ),
        "revision_comment_label": "Revision comment (optional):",
        "revision_comment_placeholder": "What changed in this revision…",
        "create_revision_button": "Create revision",
        "assembly_detected_title": "Assembly detected",
        "assembly_detected_body": (
            "This document links to {count} other files (parts/sub-assemblies):\n\n"
            "{summary}\n\n"
            "Send them automatically together with this document (parts/sub-assemblies "
            "first, this document last)?\n\n"
            "\"No\" will send ONLY this document, as before — without sub-items."
        ),
        "already_in_pdm_as": " -> ALREADY in PDM as #{number} ({name})",
        "already_linked_confirm": (
            "This document looks like an already-uploaded PDM item #{number} ({name}). "
            "Attach the current version as a new revision/update of THIS item?\n\n"
            "\"No\" opens the regular browser form (New item / Duplicate / Attach to "
            "existing)."
        ),
        "export_step_prompt": "Export and upload STEP model (3D preview)?",
        "export_pdf_prompt": "Export and upload a PDF file?",
        "new_component_browser_prompt": (
            "New component in the tree: {name}. Click OK to open the browser and fill it "
            "in (it may open in the background — check the taskbar)."
        ),
        "fetch_items_failed": "Failed to fetch the list of items: {error}",
        "fetch_projects_failed": "Failed to fetch the list of projects: {error}",
        "upload_component_failed": "Failed to send {file}: {error}",
        "link_child_failed": "Created {child}, but failed to link it under {parent}: {error}",
        "open_browser_failed": "Failed to open the browser: {error}",
        "wait_timeout": "The waiting time has expired.",
        "wait_ticket_status": "EasyPDM: waiting for the item details to be filled in in the browser...",
        "no_active_document": "No document is open.",
        "document_not_saved": "The document has not been saved yet — choose where to save it.",
        "save_failed": "Failed to save the document: {error}",
        "final_save_failed": (
            "These files could not be saved locally. References to the new names exist only "
            "in the open document — save them by hand (Ctrl+S):\n{lines}"
        ),
        "cancelled_upload": "Cancelled — the upload was aborted.",
        "nothing_sent": "Cancelled — nothing was sent.",
        "link_subitem_failed": "Failed to link one of the sub-items under the main item: {error}",
        "local_renamed_line": (
            "Local file saved under the PDM name (Save As); the old file under the "
            "original name was left untouched:\n{path}"
        ),
        "local_already_named_line": (
            "The local file was already under the correct PDM name — nothing needed to be moved:\n{path}"
        ),
        "status_revision_mismatch": (
            "The status/revision of item #{number} has already been changed on the "
            "server (revision {revision}, status 'w_pracy'), but uploading the file failed: "
            "{error}\n\nThe item in PDM now has a new revision, but still has the file from "
            "the previous version — fix this manually in the web application (upload the "
            "file again) or try again from this macro."
        ),
        "upload_blocked_review": (
            "Cannot upload — item #{number} has status \"Under review\". Wait until the "
            "review finishes (the item returns to \"In progress\"), or change the status "
            "manually in the web application."
        ),
        "status_label_sprawdzany": "Under review",
        "status_label_wydany": "Released",
        "locked_components_tail": (
            "\n\nNote: {count} already-linked component(s) in the assembly have a locked "
            "status — they were NOT updated (the assembly tree never re-sends "
            "already-existing components, but these are additionally locked by status, "
            "so if you changed them locally, upload them separately after moving the "
            "status back to \"In progress\"):\n{lines}"
        ),
        "stale_children_confirm": (
            "{count} sub-item(s) of this item exist in PDM, but are no longer in the "
            "local assembly structure (removed from the FreeCAD tree since the last "
            "upload):\n{lines}\n\nRemove these links from PDM? (The items themselves will "
            "NOT be deleted, only their attachment under this assembly.)"
        ),
    },
    "de": {
        "no_connection": "Keine Verbindung zu {url}: {reason}",
        "login_failed_no_session": "Anmeldung fehlgeschlagen — der Server hat keine Sitzung zurückgegeben.",
        "pdm_title": "PDM",
        "unnamed_fallback": "unbenannt",
        "login_dialog_title": "Anmeldung bei PDM",
        "api_address_label": "API-Adresse:",
        "username_label": "Benutzername:",
        "password_label": "Passwort:",
        "login_button": "Anmelden",
        "cancel_button": "Abbrechen",
        "assembly_update_note": "Dateien, die bereits im PDM mit dem Status \"In Arbeit\" sind, werden aktualisiert (ihre CAD-Datei ersetzt dieselbe Revision).",
        "update_step_checkbox": "Für Dateien, die bereits im PDM sind, STEP (3D-Vorschau) neu hochladen",
        "update_pdf_checkbox": "Für Dateien, die bereits im PDM sind, PDF neu hochladen",
        "not_sent_suffix": " — {status}, wird nicht gesendet",
        "locked_not_sent": "Diese Dateien werden nicht gesendet — sie sind im PDM mit einem Status, der Änderungen sperrt. Um sie zu aktualisieren, eine neue Revision anlegen oder sie aus der Prüfung nehmen:\n\n{lines}",
        "yes_button": "Ja",
        "no_button": "Nein",
        "login_missing_fields": "Geben Sie Benutzername und Passwort ein.",
        "sheet_ask_existing_page": "Das Dokument hat die Zeichnungsseite „{page}“ ohne EasyPDM-Blatt.\n\nDas EasyPDM-Blatt mit aus PDM ausgefülltem Schriftfeld darauf setzen? Die Ansichten bleiben.",
        "target_folder_dialog_title": "An PDM senden",
        "logged_in_as": "Angemeldet als: {name}",
        "logout_button": "Abmelden",
        "account_label": "Konto:",
        "target_folder_hint": (
            "Wohin sollen lokale Kopien der hochgeladenen Dokumente abgelegt werden "
            "(dieselbe Datei unter dem PDM-Namen statt des Originals)? Das ist derselbe "
            "Ort wie der Download-Ordner in EasyPDMDownload.FCMacro — es empfiehlt sich, "
            "beide gleich einzustellen."
        ),
        "choose_target_folder_caption": "Zielordner auswählen",
        "indicate_folder": "Wählen Sie einen Ordner.",
        "cannot_use_folder": "Dieser Ordner kann nicht verwendet werden: {error}",
        "logged_out_message": "Abgemeldet. Beim nächsten Ausführen des Makros werden Sie erneut zur Anmeldung aufgefordert.",
        "new_revision_title": "Neue Revision",
        "new_revision_body": (
            'Dieses Element hat den Status "Freigegeben" — es können keine Dateien '
            'hinzugefügt werden.\n\nMöchten Sie eine neue Revision erstellen (der Status '
            'wechselt zu "In Bearbeitung")?'
        ),
        "revision_comment_label": "Revisionskommentar (optional):",
        "revision_comment_placeholder": "Was hat sich in dieser Revision geändert…",
        "create_revision_button": "Revision erstellen",
        "assembly_detected_title": "Baugruppe erkannt",
        "assembly_detected_body": (
            "Dieses Dokument verknüpft mit {count} anderen Dateien (Teile/Unterbaugruppen):\n\n"
            "{summary}\n\n"
            "Sollen sie automatisch zusammen mit diesem Dokument gesendet werden (zuerst "
            "Teile/Unterbaugruppen, zuletzt dieses Dokument)?\n\n"
            "\"Nein\" sendet NUR dieses Dokument, wie bisher — ohne Unterelemente."
        ),
        "already_in_pdm_as": " -> BEREITS in PDM als #{number} ({name})",
        "already_linked_confirm": (
            "Dieses Dokument sieht aus wie das bereits hochgeladene PDM-Element Nr. "
            "{number} ({name}). Die aktuelle Version als neue Revision/Aktualisierung "
            "DIESES Elements anhängen?\n\n\"Nein\" öffnet das normale Browser-Formular "
            "(Neues Element / Duplizieren / Vorhandenem anhängen)."
        ),
        "export_step_prompt": "STEP-Modell exportieren und hochladen (3D-Vorschau)?",
        "export_pdf_prompt": "PDF-Datei exportieren und hochladen?",
        "new_component_browser_prompt": (
            "Neue Komponente im Baum: {name}. Klicken Sie OK, um den Browser zu öffnen "
            "und sie einzugeben (er kann im Hintergrund geöffnet werden — prüfen Sie die "
            "Taskleiste)."
        ),
        "fetch_items_failed": "Die Elementliste konnte nicht abgerufen werden: {error}",
        "fetch_projects_failed": "Die Projektliste konnte nicht abgerufen werden: {error}",
        "upload_component_failed": "{file} konnte nicht gesendet werden: {error}",
        "link_child_failed": "{child} wurde erstellt, konnte aber nicht unter {parent} verknüpft werden: {error}",
        "open_browser_failed": "Der Browser konnte nicht geöffnet werden: {error}",
        "wait_timeout": "Die Wartezeit ist abgelaufen.",
        "wait_ticket_status": "EasyPDM: warte auf die im Browser einzutragenden Elementdaten...",
        "no_active_document": "Kein Dokument geöffnet.",
        "document_not_saved": "Das Dokument wurde noch nicht gespeichert — wählen Sie einen Speicherort.",
        "save_failed": "Das Dokument konnte nicht gespeichert werden: {error}",
        "final_save_failed": (
            "Diese Dateien konnten lokal nicht gespeichert werden. Verweise auf die neuen Namen gibt es nur "
            "im geöffneten Dokument — bitte von Hand speichern (Strg+S):\n{lines}"
        ),
        "cancelled_upload": "Abgebrochen — der Upload wurde abgebrochen.",
        "nothing_sent": "Abgebrochen — es wurde nichts gesendet.",
        "link_subitem_failed": "Eines der Unterelemente konnte nicht unter dem Hauptelement verknüpft werden: {error}",
        "local_renamed_line": (
            "Lokale Datei unter dem PDM-Namen gespeichert (Speichern unter); die alte "
            "Datei unter dem ursprünglichen Namen blieb unverändert:\n{path}"
        ),
        "local_already_named_line": (
            "Die lokale Datei trug bereits den richtigen PDM-Namen — es musste nichts verschoben werden:\n{path}"
        ),
        "status_revision_mismatch": (
            "Status/Revision von Element #{number} wurden bereits auf dem Server geändert "
            "(Revision {revision}, Status 'w_pracy'), aber das Hochladen der Datei ist "
            "fehlgeschlagen: {error}\n\nDas Element in PDM hat jetzt eine neue Revision, "
            "aber immer noch die Datei der vorherigen Version — korrigieren Sie dies "
            "manuell in der Webanwendung (Datei erneut hochladen) oder versuchen Sie es "
            "erneut mit diesem Makro."
        ),
        "upload_blocked_review": (
            "Hochladen nicht möglich — Element #{number} hat den Status \"In Prüfung\". "
            "Warten Sie, bis die Prüfung abgeschlossen ist (das Element kehrt zu \"In "
            "Bearbeitung\" zurück), oder ändern Sie den Status manuell in der "
            "Web-Anwendung."
        ),
        "status_label_sprawdzany": "In Prüfung",
        "status_label_wydany": "Freigegeben",
        "locked_components_tail": (
            "\n\nHinweis: {count} bereits verknüpfte Komponente(n) in der Baugruppe haben "
            "einen gesperrten Status — sie wurden NICHT aktualisiert (der Baugruppenbaum "
            "sendet bereits vorhandene Komponenten nie erneut, aber diese sind zusätzlich "
            "durch ihren Status gesperrt — falls Sie sie lokal geändert haben, laden Sie "
            "sie separat hoch, nachdem der Status wieder auf \"In Bearbeitung\" gesetzt "
            "wurde):\n{lines}"
        ),
        "stale_children_confirm": (
            "{count} Unterelement(e) dieses Elements existieren im PDM, sind aber nicht "
            "mehr in der lokalen Baugruppenstruktur (seit dem letzten Hochladen aus dem "
            "FreeCAD-Baum entfernt):\n{lines}\n\nDiese Verknüpfungen aus dem PDM entfernen? "
            "(Die Elemente selbst werden NICHT gelöscht, nur ihre Zuordnung zu dieser "
            "Baugruppe.)"
        ),
    },
}


def t(key, **kwargs):
    text = TRANSLATIONS.get(LANG, TRANSLATIONS["en"]).get(key, TRANSLATIONS["en"].get(key, key))
    return text.format(**kwargs) if kwargs else text


PARAM_GROUP = "User parameter:BaseApp/EasyPDM"
DEFAULT_BASE_URL = "http://localhost:5000/api"
SESSION_COOKIE_NAME = "pdm_session"
# Klucz pozycji dokumentu nadrzędnego na liście postępu. Stała, bo odhaczany jest w innym
# miejscu (koniec run()) niż dodawany do listy (process_assembly_tree), a literał w dwóch
# miejscach rozjechałby się przy pierwszej zmianie.
TOP_DOCUMENT_PROGRESS_KEY = "__top__"

# Identyfikator JEDNEGO biegu makra i informacja, czy jakaś karta przeglądarki na TEJ maszynie
# już go zna. Karta podejmuje wyłącznie prośby ze swoim runId — bez tego wystarczyło, że to samo
# konto było zalogowane w przeglądarce na DRUGIM komputerze, żeby prośba stąd trafiła do karty
# tam i pokazała formularz komuś innemu (zgłoszone z praktyki).
#
# Dlatego PIERWSZY komponent biegu zawsze otwiera kartę — i dopiero ta karta, znając runId,
# obsługuje resztę bez kolejnych kart i bez okien.
# "cancelled" -- użytkownik kliknął „Anuluj" w panelu postępu, zob. transfer_cancelled.
_RUN = {"id": None, "tab_opened": False, "cancelled": False, "top_preset": None, "locked_shown": False,
        "progress_started": False}


def run_id():
    if _RUN["id"] is None:
        _RUN["id"] = str(uuid.uuid4())
    return _RUN["id"]


class AuthError(RuntimeError):
    """Brak sesji albo sesja wygasła/została unieważniona — trzeba się (ponownie) zalogować.
    Odróżniona od zwykłego RuntimeError, żeby ensure_logged_in() wiedziało kiedy pokazać
    okno logowania, zamiast tylko wyświetlić czerwony komunikat błędu."""
    pass

# Dopasowuje własną konwencję nazewnictwa "numer (nazwa).REWIZJA" (nadawaną plikom/etykietom
# przez to samo makro po wysłaniu do PDM) — np. "76 (RewizjaTest).C". Jeśli dokument został
# ponownie otwarty z takiego pliku, nazwa/etykieta NIE jest już samą nazwą elementu, tylko
# tym pełnym formatem — trzeba wyłuskać numer, żeby rozpoznać, o który element chodzi.
# Nazwa pliku PDM to "NUMER (nazwa).REWIZJA.rozszerzenie", gdzie NUMER może mieć literowy
# prefiks rodzaju i zera wiodace (Ustawienia -> Nazewnictwo), np. "C0005 (Wspornik).A.FCStd".
# Prefiks i zera sa tu tylko ozdoba -- do odpytania API liczy sie sama liczba, a int() zjada
# zera wiodace. Stare nazwy bez prefiksu ("5 (Wspornik)") dalej pasuja, bo prefiks jest
# opcjonalny.
# Czlon "(nazwa)" jest OPCJONALNY -- po wylaczeniu nazwy elementu w nazwie rekordu dokument
# nazywa sie samym numerem ("C0005.A"). Gdy nazwy nie ma, nie da sie potwierdzic dopasowania
# nazwa (zob. match_existing_item) i zostaje sam numer -- ryzyko falszywego trafienia jest tu
# jednak male, bo "C0005.A" to juz konwencja PDM, a nie przypadkowa nazwa uzytkownika.
_REVISION_NAME_PATTERN = re.compile(r"^(?P<prefix>[A-Za-z]*)(?P<number>\d+)\s*(?:\((?P<name>.+)\))?(?:\.[A-Za-z]+)?$")


def _record_key(text):
    """Nazwa rekordu sprowadzona do postaci porównywalnej: bez spacji (stara konwencja
    "5 (Wspornik)" i nowa "5(Wspornik)" to ten sam rekord) i bez wielkości liter."""
    return re.sub(r"\s+", "", text or "").lower()


def label_matches_item(label, item):
    """Czy etykieta dokumentu to DOKŁADNIE nazwa rekordu tego elementu (z ewentualną literą
    rewizji na końcu), a nie tylko coś, z czego da się wyłuskać ten sam numer.

    _REVISION_NAME_PATTERN dopuszcza dowolne litery przed numerem (prefiks rodzaju, np. "C"
    w "C0005") i opcjonalny człon "(nazwa)", więc sam w sobie łapie też zwykłe nazwy
    użytkownika: "testc2" czytał jako prefiks "testc" + numer 2, bez nazwy do sprawdzenia, i
    podpinał plik pod istniejący element #2 (zgłoszone z praktyki). Pełna nazwa rekordu z
    serwera (prefiks, zera wiodące, nazwa w nawiasie albo jej brak -- zob. ItemNumbering)
    rozstrzyga jednoznacznie: "testc2" nigdy nie jest równe "2(Płyty)"."""
    base = re.sub(r"\.[A-Za-z]+$", "", label or "")
    return _record_key(base) == _record_key(record_name_text(item))


def record_name_text(item, fallback_name=""):
    """Pelna NAZWA REKORDU tak, jak ma wygladac w nazwie pliku -- gotowa z serwera
    (recordName: prefiks rodzaju, zera wiodace i -- zaleznie od ustawienia zamrozonego na
    elemencie -- nazwa elementu w nawiasie, zob. ItemNumbering po stronie API). Zapas na
    stara konwencje "numer(nazwa)" zostaje dla starszego serwera, ktory tego pola nie zwraca."""
    record = item.get("recordName")
    if record:
        return str(record)
    name = fallback_name or item.get("fileName", "") or item.get("name", "")
    number = item.get("itemNumberLabel") or item.get("itemNumber", "")
    return "%s(%s)" % (number, name)


def get_base_url():
    return App.ParamGet(PARAM_GROUP).GetString("ApiBaseUrl", DEFAULT_BASE_URL).rstrip("/")


def set_base_url(url):
    App.ParamGet(PARAM_GROUP).SetString("ApiBaseUrl", url.rstrip("/"))


def get_session_token():
    return App.ParamGet(PARAM_GROUP).GetString("SessionToken", "") or None


def set_session_token(token):
    App.ParamGet(PARAM_GROUP).SetString("SessionToken", token or "")


def get_saved_username():
    return App.ParamGet(PARAM_GROUP).GetString("SavedDisplayName", "") or None


def set_saved_username(name):
    App.ParamGet(PARAM_GROUP).SetString("SavedDisplayName", name or "")


def get_download_folder():
    """Ostatnio użyty folder docelowy — WSPÓLNA preferencja z EasyPDMDownload.FCMacro
    (ten sam klucz w tej samej grupie), więc oba makra mogą celować w to samo miejsce:
    pobrane pliki i lokalne kopie (Save As) wysyłanych dokumentów lądują razem."""
    folder = App.ParamGet(PARAM_GROUP).GetString("DownloadFolder", "")
    return folder or None


def set_download_folder(folder):
    App.ParamGet(PARAM_GROUP).SetString("DownloadFolder", folder or "")


def _auth_headers():
    token = get_session_token()
    return {"Cookie": f"{SESSION_COOKIE_NAME}={token}"} if token else {}


def _read_error_body(http_error):
    try:
        return http_error.read().decode("utf-8") or str(http_error)
    except Exception:
        return str(http_error)


def _raise_for_http_error(e):
    if e.code == 401:
        raise AuthError(_read_error_body(e))
    raise RuntimeError(_read_error_body(e))


def api_get(path):
    req = request.Request(get_base_url() + path, method="GET", headers=_auth_headers())
    try:
        with request.urlopen(req, timeout=10) as resp:
            body = resp.read().decode("utf-8")
            return json.loads(body) if body else None
    except error.HTTPError as e:
        _raise_for_http_error(e)
    except error.URLError as e:
        raise RuntimeError(t("no_connection", url=get_base_url(), reason=e.reason))



def api_get_binary(path):
    """Like api_get, but returns the raw bytes (the company logo for the drawing sheet)."""
    req = request.Request(get_base_url() + path, method="GET", headers=_auth_headers())
    try:
        with request.urlopen(req, timeout=60) as resp:
            return resp.read()
    except error.HTTPError as e:
        _raise_for_http_error(e)
    except error.URLError as e:
        raise RuntimeError(t("no_connection", url=get_base_url(), reason=e.reason))

def api_post_json(path, payload):
    data = json.dumps(payload).encode("utf-8")
    headers = {"Content-Type": "application/json"}
    headers.update(_auth_headers())
    req = request.Request(get_base_url() + path, data=data, method="POST", headers=headers)
    try:
        with request.urlopen(req, timeout=15) as resp:
            body = resp.read().decode("utf-8")
            return json.loads(body) if body else None
    except error.HTTPError as e:
        _raise_for_http_error(e)
    except error.URLError as e:
        raise RuntimeError(t("no_connection", url=get_base_url(), reason=e.reason))


def api_upload_file(path, file_path, field_name="file", override_filename=None, extra_fields=None):
    boundary = f"----EasyPDMUploadBoundary{uuid.uuid4().hex}"
    with open(file_path, "rb") as f:
        file_content = f.read()
    filename = override_filename or os.path.basename(file_path)

    parts = []
    for key, value in (extra_fields or {}).items():
        parts.append(f"--{boundary}\r\n".encode("utf-8"))
        parts.append(f'Content-Disposition: form-data; name="{key}"\r\n\r\n'.encode("utf-8"))
        parts.append(f"{value}\r\n".encode("utf-8"))
    parts += [
        f"--{boundary}\r\n".encode("utf-8"),
        f'Content-Disposition: form-data; name="{field_name}"; filename="{filename}"\r\n'.encode("utf-8"),
        b"Content-Type: application/octet-stream\r\n\r\n",
        file_content,
        f"\r\n--{boundary}--\r\n".encode("utf-8"),
    ]
    payload = b"".join(parts)

    headers = {"Content-Type": f"multipart/form-data; boundary={boundary}"}
    headers.update(_auth_headers())
    req = request.Request(get_base_url() + path, data=payload, method="POST", headers=headers)
    try:
        with request.urlopen(req, timeout=60) as resp:
            body = resp.read().decode("utf-8")
            return json.loads(body) if body else None
    except error.HTTPError as e:
        _raise_for_http_error(e)
    except error.URLError as e:
        raise RuntimeError(t("no_connection", url=get_base_url(), reason=e.reason))


def api_patch_json(path, payload):
    data = json.dumps(payload).encode("utf-8")
    headers = {"Content-Type": "application/json"}
    headers.update(_auth_headers())
    req = request.Request(get_base_url() + path, data=data, method="PATCH", headers=headers)
    try:
        with request.urlopen(req, timeout=15) as resp:
            body = resp.read().decode("utf-8")
            return json.loads(body) if body else None
    except error.HTTPError as e:
        _raise_for_http_error(e)
    except error.URLError as e:
        raise RuntimeError(t("no_connection", url=get_base_url(), reason=e.reason))


def api_delete(path):
    req = request.Request(get_base_url() + path, method="DELETE", headers=_auth_headers())
    try:
        with request.urlopen(req, timeout=15) as resp:
            body = resp.read().decode("utf-8")
            return json.loads(body) if body else None
    except error.HTTPError as e:
        _raise_for_http_error(e)
    except error.URLError as e:
        raise RuntimeError(t("no_connection", url=get_base_url(), reason=e.reason))


# ============================================================================
# Postęp wysyłki/pobierania pokazywany w aplikacji webowej jako lista plików odhaczana w
# trakcie pracy makra (zob. TransferProgressStore.cs / TransferProgressPanel.tsx).
#
# CELOWO nie korzysta z api_post_json/api_patch_json: tamte rzucają wyjątkiem przy błędzie
# HTTP, a raportowanie postępu NIE MOŻE przerwać wysyłki. Żadna awaria tutaj — brak
# połączenia, zrestartowany serwer, starsza wersja bez tych endpointów — nie ma prawa
# zatrzymać tego, po co użytkownik uruchomił makro. Stąd własny, cichy wariant.
# ============================================================================

def _progress_send(method, path, payload):
    try:
        data = json.dumps(payload).encode("utf-8")
        headers = {"Content-Type": "application/json"}
        headers.update(_auth_headers())
        req = request.Request(get_base_url() + path, data=data, method=method, headers=headers)
        with request.urlopen(req, timeout=10):
            pass
    except Exception:
        pass


def progress_start(kind, entries, edges=None):
    """entries: lista par (klucz, etykieta). Zgłaszana w CAŁOŚCI, zanim cokolwiek poleci —
    bez pełnej listy od początku pasek postępu kłamałby ("3 z 3" zamieniałoby się w "3 z 9",
    gdy znajdzie się kolejny poziom drzewa).

    edges (opcjonalnie): pary (klucz rodzica, klucz dziecka), po których serwer układa listę
    w drzewo z wcięciami (zob. ProgressTree.cs). Bez nich lista zostaje płaska, jak dotąd."""
    if not entries:
        return
    payload = {
        "kind": kind,
        "entries": [{"key": k, "label": l} for k, l in entries],
    }
    if edges:
        payload["edges"] = [{"parent": p, "child": c} for p, c in edges]
    _progress_send("PUT", "/progress", payload)
    _RUN["progress_started"] = True


def progress_mark(key, status):
    """status: "active" | "done" | "failed" | "skipped" """
    if key:
        _progress_send("PATCH", "/progress", {"key": key, "status": status})


def transfer_cancelled():
    """Czy użytkownik kliknął „Anuluj" w panelu postępu w przeglądarce.

    Serwer niczego sam nie przerywa — tylko zapisuje prośbę (POST /api/progress/cancel) — więc
    to makro pyta o nią przy każdym odpytaniu o formularz i przed każdym kolejnym plikiem. Plik,
    który akurat leci, zostaje dokończony: przerwanie w połowie zostawiłoby go uszkodzonego.

    Pierwsze „tak" jest zapamiętywane, żeby nie pytać serwera za każdym razem. Każdy błąd
    (brak połączenia, starszy serwer bez tego endpointu) znaczy „nie anulowano" — to wygoda,
    która nie ma prawa zatrzymać przesyłania."""
    if not _RUN["cancelled"]:
        try:
            probe = api_get("/progress/cancelled")
            if probe and probe.get("cancelled") == 1:
                _RUN["cancelled"] = True
                App.Console.PrintMessage(
                    "EasyPDM: anulowano w przegladarce -- zatrzymuje sie przed kolejnym plikiem\n"
                )
        except Exception:
            pass
    return _RUN["cancelled"]


def progress_finish():
    _progress_send("POST", "/progress/finish", {})


def progress_label_for(path):
    """Sama nazwa pliku z rozszerzeniem — pełna ścieżka nie mieści się w panelu i nic nie wnosi."""
    return os.path.basename(path) if path else "(bez nazwy)"


def api_login(username, password):
    """Loguje się (POST /api/auth/login) i zapisuje token sesji w preferencjach FreeCAD —
    ten sam mechanizm co ApiBaseUrl, więc logowanie przetrwa restart FreeCAD, dopóki sesja
    jest ważna po stronie serwera (30 dni, tak samo jak w aplikacji webowej). Zwraca dict
    użytkownika ({"username", "displayName", "role", ...}, tak jak POST /api/auth/login)."""
    # Logowanie makra (POST /api/auth/macro-login) daje osobny token makra — widoczny i
    # odwoływalny w Ustawienia -> Użytkownicy — zamiast sesji przeglądarki. Odpowiedź ma ten sam
    # kształt co /auth/login, więc reszta działa bez zmian. Serwer sprzed 0.8 nie zna tej ścieżki
    # (404) — wtedy zwykłe logowanie, jak dotąd.
    data = json.dumps({"username": username, "password": password, "client": "FreeCAD Upload"}).encode("utf-8")

    def _post_login(path):
        req = request.Request(
            get_base_url() + path, data=data, method="POST",
            headers={"Content-Type": "application/json"},
        )
        with request.urlopen(req, timeout=10) as resp:
            raw = resp.read().decode("utf-8")
            return (json.loads(raw) if raw else {}), resp.headers.get("Set-Cookie", "")

    try:
        try:
            user, set_cookie_header = _post_login("/auth/macro-login")
        except error.HTTPError as e:
            if e.code != 404:
                raise
            user, set_cookie_header = _post_login("/auth/login")
    except error.HTTPError as e:
        raise RuntimeError(_read_error_body(e))
    except error.URLError as e:
        raise RuntimeError(t("no_connection", url=get_base_url(), reason=e.reason))

    # Token najpierw z treści odpowiedzi (pole "sessionToken" — także dla tokenu makra), potem
    # z ciasteczka, jak dotąd.
    token = user.get("sessionToken") or None
    for part in ([] if token else set_cookie_header.split(";")):
        part = part.strip()
        if part.startswith(f"{SESSION_COOKIE_NAME}="):
            token = part[len(SESSION_COOKIE_NAME) + 1:]
            break
    if not token:
        raise RuntimeError(t("login_failed_no_session"))

    set_session_token(token)
    set_saved_username(user.get("displayName") or user.get("username") or username)
    return user


def api_logout():
    """Unieważnia sesję po stronie serwera (POST /api/auth/logout) i zawsze czyści też
    lokalnie zapisany token — nawet jeśli wywołanie się nie powiedzie (np. brak połączenia),
    użytkownik i tak przestaje być "zalogowany" z punktu widzenia tego makra, więc kolejne
    uruchomienie poprosi o ponowne logowanie."""
    token = get_session_token()
    if token:
        req = request.Request(
            get_base_url() + "/auth/logout", method="POST", headers=_auth_headers()
        )
        try:
            request.urlopen(req, timeout=10)
        except Exception:
            pass
    set_session_token(None)
    set_saved_username(None)


def ensure_logged_in():
    """Sprawdza, czy zapisana sesja jest jeszcze ważna (GET /api/auth/me); jeśli jej nie ma
    albo wygasła/została unieważniona, pokazuje okno logowania. Zwraca True, jeśli po
    wywołaniu tej funkcji jest aktywna sesja (można kontynuować), False jeśli użytkownik
    anulował logowanie."""
    if get_session_token():
        try:
            me = api_get("/auth/me")
            # Odświeżamy zapisaną nazwę z /auth/me — bez tego, jeśli token pochodzi z sesji
            # zapisanej wcześniej BEZ przechodzenia przez api_login() w TEJ instalacji (np.
            # ustawiony ręcznie, albo zapisany przez starszą wersję makra), SavedDisplayName
            # zostawałoby puste na zawsze, mimo w pełni ważnej sesji — okno pokazywałoby
            # "Zalogowano jako: ?".
            if me:
                set_saved_username(me.get("displayName") or me.get("username"))
            return True
        except AuthError:
            set_session_token(None)  # token wygasł/nieważny — nie próbuj go już więcej
        except Exception:
            # Np. brak połączenia — nie blokujemy logowaniem na etapie samego sprawdzenia,
            # błąd i tak wypłynie czytelnie przy pierwszym realnym wywołaniu API.
            return True

    dlg = LoginDialog()
    return dlg.exec() == QtWidgets.QDialog.Accepted


def sanitize_filename(name):
    cleaned = re.sub(r'[\\/:*?"<>|]+', "_", name).strip()
    return cleaned or t("unnamed_fallback")


def revision_label(n):
    """Rewizje jako wielkie litery zamiast cyfr: 1->A, 2->B, ..., 26->Z, 27->AA...
    (jak numeracja kolumn arkusza) — sama liczba w bazie (revisionNumber) się nie zmienia.
    Ta sama konwersja jest po stronie frontu w api/types.ts (revisionLabel)."""
    n = int(n)
    label = ""
    while n > 0:
        n, remainder = divmod(n - 1, 26)
        label = chr(65 + remainder) + label
    return label or "A"


def _document_size(doc):
    """Rozmiar pliku dokumentu na dysku w bajtach, albo None gdy dokument nie był jeszcze
    zapisany (wtedy nie ma czego mierzyć). Tylko do ostrzeżenia o długim eksporcie STEP —
    błąd tutaj nie może zatrzymać wysyłki."""
    try:
        path = getattr(doc, "FileName", "") or ""
        return os.path.getsize(path) if path and os.path.exists(path) else None
    except Exception:
        return None


def _cad_item_type(doc):
    """"assembly", jeśli dokument linkuje (App::Link) do innych ZAPISANYCH plików, inaczej "part".

    Służy wyłącznie do wstępnego zaznaczenia przycisku w oknie dodawania. Bez tego okno
    startowało bez żadnego wyboru i złożenie łatwo powstawało jako Część — a do Części nie da
    się nic podpiąć w strukturze, więc podpinanie komponentów kończyło się błędem 400 i cała
    struktura BOM nie powstawała. Ta sama reguła co przy wykrywaniu drzewa, więc typ zgadza się
    z tym, co makro faktycznie zaraz zrobi.

    Błąd tutaj nie może niczego zatrzymać — w najgorszym razie okno startuje jak dotąd, bez
    wyboru."""
    try:
        return "assembly" if _iter_external_link_targets(doc) else "part"
    except Exception:
        return ""


def open_in_browser(url):
    """Otwiera adres w przeglądarce tak, żeby wyszła NA WIERZCH.

    Dotąd było to `webbrowser.open`, który uruchamia po prostu `xdg-open`. Pod Wayland nowy
    proces dostaje fokus tylko wtedy, gdy uruchamiający przekaże mu token aktywacji
    (xdg-activation) — a `webbrowser` żadnego nie przekazuje. KDE otwierało więc kartę w tle
    i jedynie podświetlało przeglądarkę na pasku zadań; trzeba było ją wyciągać ręcznie
    (zgłoszone z praktyki, KDE/Wayland).

    `QDesktopServices.openUrl` robi to samo, ale przez Qt, który od wersji 6.6 prosi
    kompozytor o token w imieniu FreeCAD-a i przekazuje go dalej. Token jest ważny, bo
    w tej chwili fokus ma FreeCAD — użytkownik właśnie uruchomił w nim makro.

    `webbrowser.open` zostaje jako zapas: gdy Qt nie ma tej funkcji albo odmówi (stare
    FreeCAD, brak środowiska graficznego), zachowanie jest dokładnie takie jak dotąd."""
    try:
        try:
            from PySide6 import QtGui
        except ImportError:
            try:
                from PySide2 import QtGui
            except ImportError:
                from PySide import QtGui
        if QtGui.QDesktopServices.openUrl(QtCore.QUrl(url)):
            return
    except Exception:
        pass
    webbrowser.open(url)


# Pełny <title> aplikacji (EasyPDM.Web/index.html — musi się z nim zgadzać co do znaku).
# Okno przeglądarki dopasowujemy po POCZĄTKU
# tytułu, bo przeglądarki doklejają swoją nazwę na końcu. NIE po samym "EasyPDM": u autora
# okno Shotcuta miało w tytule "EasyPDM2.mlt", więc takie dopasowanie wyciągnęłoby na
# wierzch montaż wideo zamiast przeglądarki (wyłapane sondą na żywej sesji KDE).
APP_WINDOW_TITLE = "EasyPDM — CAD item browser"

# Skrypt dla KWin. Szuka zwykłego okna, którego tytuł zaczyna się od tytułu aplikacji, i
# aktywuje je. Plasma 6 ma windowList/activeWindow, Plasma 5 clientList/activeClient.
_KWIN_RAISE_SCRIPT = """
const wins = workspace.windowList ? workspace.windowList() : workspace.clientList();
for (const w of wins) {
    if (w.normalWindow && (%(match)s)) {
        if (workspace.activeWindow !== undefined) workspace.activeWindow = w;
        else workspace.activeClient = w;
        break;
    }
}
"""

# Okno FreeCAD-a: najpierw po numerze procesu, a gdy nie pasuje (FreeCAD z Flatpaka ma w
# piaskownicy inny pid niż ten, który widzi KWin) -- po klasie okna. Kopia z
# EasyPDMDownload.FCMacro.
_KWIN_FREECAD_MATCH = (
    "w.pid === %(pid)d || !wins.some(function (x) { return x.normalWindow && x.pid === %(pid)d; })"
    " && (w.resourceClass || \"\").toLowerCase().indexOf(\"freecad\") >= 0"
)


def _raise_via_kwin(match_js=None):
    """Wyciąga okno przeglądarki na wierzch przez KWin — działa na KDE, także pod Wayland.

    Pod Wayland żadna aplikacja nie może sama aktywować okna innej. Może to jednak zrobić
    kompozytor, a KWin przyjmuje skrypty przez DBus (org.kde.KWin /Scripting) — tak samo
    działa `kdotool`. Skrypt jest zapisywany do pliku tymczasowego, wczytywany, uruchamiany i
    od razu zdejmowany.

    Potrzebne, bo token aktywacji (zob. open_in_browser) pomaga tylko przeglądarce
    URUCHAMIANEJ od zera. Gdy już działa, `xdg-open` startuje jedynie jej krótki proces
    pośredniczący, który przekazuje adres do działającego okna — a czy to okno skorzysta z
    tokenu, zależy od przeglądarki (zgłoszone z praktyki: zamknięta przeglądarka wychodziła na
    wierzch, otwarta — nie).

    `match_js` to warunek JS na oknie `w`; domyślnie okno przeglądarki z EasyPDM (po
    początku tytułu). Ten sam mechanizm wyciąga na wierzch sam FreeCAD -- zob. _show_on_top.

    Zwraca True, gdy skrypt udało się uruchomić — nie mówi, czy okno znalazł. Poza KDE (brak
    gdbus albo usługi org.kde.KWin) po prostu zwraca False."""
    if shutil.which("gdbus") is None:
        return False
    plugin = "easypdm-raise-browser"
    path = None

    def call(object_path, method, *args):
        return subprocess.run(
            ["gdbus", "call", "--session", "--dest", "org.kde.KWin",
             "--object-path", object_path, "--method", method, *args],
            capture_output=True, text=True, timeout=3,
        )

    try:
        fd, path = tempfile.mkstemp(prefix="easypdm-kwin-", suffix=".js")
        with os.fdopen(fd, "w", encoding="utf-8") as f:
            # json.dumps daje poprawny literał JS, z polskimi znakami jako \uXXXX.
            if match_js is None:
                match_js = '(w.caption || "").indexOf(%s) === 0' % json.dumps(APP_WINDOW_TITLE)
            f.write(_KWIN_RAISE_SCRIPT % {"match": match_js})
        # Gdyby poprzednie uruchomienie zostawiło skrypt wczytany, loadScript by odmówił.
        call("/Scripting", "org.kde.kwin.Scripting.unloadScript", plugin)
        loaded = call("/Scripting", "org.kde.kwin.Scripting.loadScript", path, plugin)
        found = re.search(r"-?\d+", loaded.stdout or "")
        if loaded.returncode != 0 or not found or int(found.group()) < 0:
            return False
        ran = call(f"/Scripting/Script{found.group()}", "org.kde.kwin.Script.run")
        call("/Scripting", "org.kde.kwin.Scripting.unloadScript", plugin)
        return ran.returncode == 0
    except Exception:
        return False
    finally:
        if path:
            try:
                os.remove(path)
            except OSError:
                pass


def _focus_browser_window():
    """Przenosi okno przeglądarki z EasyPDM na wierzch — odpowiednik `AppActivate "EasyPDM"`
    z makr SolidWorks/Inventor. Tylko dla Linuksa; na Windowsie nie ma tu czego naprawiać.

    Najpierw KWin (KDE, X11 i Wayland — zob. _raise_via_kwin), potem `wmctrl`/`xdotool`
    (inne środowiska pod X11). Poza tym — GNOME pod Wayland — nie zadziała nic, bo kompozytor
    na to nie pozwala; od strony przeglądarki czeka wtedy powiadomienie systemowe, którego
    kliknięcie przełącza na kartę."""
    if _raise_via_kwin():
        return True
    for command in (["wmctrl", "-a", APP_WINDOW_TITLE],
                    ["xdotool", "search", "--name", "^" + re.escape(APP_WINDOW_TITLE), "windowactivate"]):
        if shutil.which(command[0]) is None:
            continue
        try:
            done = subprocess.run(command, timeout=3,
                                  stdout=subprocess.DEVNULL, stderr=subprocess.DEVNULL)
            if done.returncode == 0:
                return True
        except Exception:
            pass
    return False


def publish_cad_request(ticket, name, item_type=None, material=None, document_size=None, component=False,
                        suggested_item_number=None):
    """Zostawia na serwerze prośbę o formularz dla JUŻ OTWARTEJ karty przeglądarki i czeka
    chwilę na sygnał, że ktoś ją podjął. Zwraca True, gdy podjęta — wtedy NIE otwieramy
    nowej karty.

    Po co: wysyłając złożenie, makro potrzebuje formularza dla każdego nowego komponentu.
    Dotąd otwierało na to osobną kartę, a przed każdą musiało pokazać okno "OK" — nie dla
    potwierdzenia, lecz dlatego, że Windows przepuszcza przejęcie fokusu tylko PIERWSZEMU
    programowemu otwarciu przeglądarki w danym biegu. Przy kilkudziesięciu częściach to
    kilkadziesiąt kliknięć i tyleż kart. Otwarta karta i tak odpytuje serwer, więc wystarczy
    jej prośbę podać.

    Czekanie jest krótkie: sprawdzamy tylko, CZY KTOŚ PATRZY, a nie czy wypełnił formularz —
    tym zajmuje się wait_for_ticket. Gdy nikt nie podejmie (przeglądarka zamknięta),
    kasujemy prośbę i wracamy do starej ścieżki.

    Błąd tutaj nie może niczego zatrzymać: w najgorszym razie zwracamy False i wszystko idzie
    jak przed tą zmianą."""
    import time

    # Dopóki żadna karta na TEJ maszynie nie zna runId tego biegu, nie ma komu podać prośby —
    # a podanie jej "komukolwiek" trafiałoby w przeglądarkę na innym komputerze zalogowaną tym
    # samym kontem. Pierwszy komponent biegu idzie więc starą ścieżką.
    if not _RUN["tab_opened"]:
        App.Console.PrintMessage(
            "EasyPDM: prosba o formularz pominieta -- zadna karta tego biegu jeszcze nie istnieje\n"
        )
        return False

    payload = {"runId": run_id(), "ticket": ticket, "mode": "create"}
    if name:
        payload["name"] = name
    if item_type:
        payload["itemType"] = item_type
    if material:
        payload["material"] = material
    if document_size:
        payload["documentSize"] = document_size
    # Komponent złożenia: miejsce w strukturze wynika z drzewa CAD, więc przeglądarka nie
    # pokazuje dla niego wyboru projektu ani rodzica (zob. build_browser_create_url).
    if component:
        payload["component"] = True
    if suggested_item_number is not None:
        payload["suggestedItemNumber"] = int(suggested_item_number)

    try:
        data = json.dumps(payload).encode("utf-8")
        headers = {"Content-Type": "application/json"}
        headers.update(_auth_headers())
        req = request.Request(get_base_url() + "/cad-requests", data=data, method="PUT", headers=headers)
        with request.urlopen(req, timeout=10):
            pass
    except Exception as e:
        # Bez tego wpisu nie da sie odroznic "serwer odrzucil prosbe" od "nikt nie patrzyl":
        # oba konczyly sie po cichu otwarciem nowej karty, a zgloszenie brzmialo tak samo
        # ("otwiera nowe okno przy kazdym pliku").
        App.Console.PrintMessage(f"EasyPDM: prosba o formularz nie zostala przyjeta przez serwer: {e}\n")
        return False

    deadline = time.time() + 6.0
    last_error = None
    while time.time() < deadline:
        time.sleep(0.4)
        try:
            probe = api_get(f"/cad-requests/taken?ticket={quote(ticket)}")
            if probe and probe.get("taken") == 1:
                App.Console.PrintMessage(f"EasyPDM: formularz dla '{name}' podjela otwarta karta\n")
                # Karta formularz pokazala, ale fokus zostal w FreeCAD -- oddajemy go tam,
                # gdzie teraz trzeba cos wpisac.
                #
                # Tylko na Linuksie: to jedyny system, na którym wmctrl/xdotool w ogóle mają
                # sens. Na Windowsie nie ma czego naprawiać — przeglądarka, która właśnie
                # dostała formularz, zostaje na wierzchu, bo żaden proces w tle (a FreeCAD
                # wtedy w tle jest) nie może jej odebrać fokusu. Wcześniej ta próba szła
                # wszędzie i na Windowsie przy każdym komponencie zostawiała w logu
                # linuksowe wyjaśnienie, które tam nie miało sensu.
                if sys.platform.startswith("linux") and not _focus_browser_window():
                    App.Console.PrintMessage(
                        "EasyPDM: nie udalo sie przelaczyc na przegladarke"
                        " (brak wmctrl/xdotool albo sesja Wayland) -- przejdz do niej recznie\n"
                    )
                return True
        except Exception as e:
            last_error = e

    App.Console.PrintMessage(
        f"EasyPDM: nikt nie podjal prosby o formularz dla '{name}' w ciagu 6 s"
        f" -- otwieram nowa karte{'' if last_error is None else f' (ostatni blad odpytania: {last_error})'}\n"
    )

    try:
        headers = _auth_headers()
        req = request.Request(get_base_url() + f"/cad-requests?ticket={quote(ticket)}", method="DELETE", headers=headers)
        with request.urlopen(req, timeout=10):
            pass
    except Exception:
        pass
    return False


def build_browser_create_url(name, ticket, suggested_item_number=None, document_size=None, item_type=None, component=False, material=None):
    """Adres, pod którym otwiera się przeglądarka systemowa zamiast natywnego formularza
    właściwości (zob. wait_for_ticket/submit_via_browser) — most logowania
    bilet->ciasteczko (GET /api/auth/browser-login) plus deep-link
    "?ticket=&name=&suggestedItemNumber=" (App.tsx / pending-create-ticket.ts w aplikacji
    webowej; UWAGA: to DWA różne bilety pod tą samą nazwą parametru na dwóch różnych
    poziomach tego samego URL-a -- "ticket" w query stringu /auth/browser-login to
    jednorazowy bilet logowania z POST /auth/browser-bridge-ticket, "ticket" wewnątrz
    zakodowanego "redirect" to bilet korelacji tworzenia elementu, przekazywany jako
    argument tej funkcji). Bilet logowania (NIE sam token sesji -- ten nigdy nie ląduje w
    URL-u, więc nie zostaje w historii przeglądarki) jest jednorazowy i krótkotrwały: makro
    dostaje go świeżo od API tuż przed otwarciem przeglądarki (zob. POST
    /browser-bridge-ticket), a GET /browser-login zużywa go przy pierwszym użyciu. CELOWO
    bez projektu/rodzica/typu/wyboru "nowy czy istniejący" — to WSZYSTKO wybiera się w
    przeglądarce: albo zwykłą, ręczną nawigacją i przyciskiem "Dodaj" tam, gdzie akurat ma
    sens (dokładnie jak przy ręcznym dodawaniu elementu przez człowieka), albo przez baner
    "oczekujące żądanie z makra" i jego opcję dogrania do istniejącego elementu (zob.
    PendingTicketBanner) — bilet dołącza się do NAJBLIŻSZEJ z tych dwóch akcji, niezależnie
    w jakim projekcie/miejscu drzewa. "suggested_item_number" to PODPOWIEDŹ (nie
    automatyczna decyzja) dla banera — numer elementu, jeśli etykieta lokalnego dokumentu
    wygląda jak już wcześniej wysłany przez to samo makro (zob. match_existing_item w
    submit_via_browser). Frontend i API dzielą jeden origin (Program.cs serwuje wwwroot/ z
    tego samego procesu), więc "redirect" to zawsze ścieżka względna zaczynająca się od "/"
    — dokładnie to, co GET /auth/browser-login akceptuje (odrzuca wszystko inne jako
    potencjalny open-redirect)."""
    deep_link_params = {"ticket": ticket}
    if name:
        deep_link_params["name"] = name
    if suggested_item_number is not None:
        deep_link_params["suggestedItemNumber"] = str(suggested_item_number)
    # Rozmiar dokumentu służy WYŁĄCZNIE do ostrzeżenia pod opcją eksportu STEP: ten eksport
    # robi CAD, zanim cokolwiek poleci na serwer, i przy dużym modelu trwa minuty. Serwer tej
    # liczby nie zna — w tym momencie nic jeszcze nie zostało zapisane ani wysłane.
    if document_size:
        deep_link_params["documentSize"] = str(document_size)
    # Typ rozpoznany z samego dokumentu — przeglądarka zaznacza wtedy właściwy przycisk
    # zamiast startować bez wyboru (zob. _cad_item_type).
    if item_type:
        deep_link_params["itemType"] = item_type
    # Materiał z modelu podstawiony w formularzu (pole zablokowane) -- jak w makrach SolidWorks
    # i Inventor. Po wysyłce i tak trafia do elementu, zob. _push_mass_and_material.
    if material:
        deep_link_params["material"] = material
    # Komponent złożenia trafia do projektu razem z elementem głównym, a pod rodzica podpina
    # go samo makro według drzewa CAD. Wybór projektu/rodzica w przeglądarce dla każdej
    # części z osobna pozwalał zbudować strukturę, która nie odpowiada złożeniu.
    if component:
        deep_link_params["component"] = "1"
    # Identyfikator biegu: karta go zapamiętuje i od tej chwili podejmuje prośby tego biegu bez
    # otwierania kolejnych kart.
    deep_link_params["runId"] = run_id()
    _RUN["tab_opened"] = True
    redirect_path = "/?" + urlencode(deep_link_params)

    login_ticket = api_post_json("/auth/browser-bridge-ticket", {})["ticket"]
    login_params = {"ticket": login_ticket, "redirect": redirect_path}
    return f"{get_base_url()}/auth/browser-login?{urlencode(login_params)}"


# ============================================================
# Wykrywanie złożenia z App::Link (odnośniki do zewnętrznych, zapisanych plików .FCStd —
# standardowy sposób budowania złożeń w workbenchu Assembly/Assembly4). Pozwala wysłać całe
# drzewo złożenia jednym uruchomieniem makra: najpierw wszystkie części/pod-złożenia
# (liście najpierw), na końcu główny dokument.
# ============================================================
def _iter_external_link_targets(doc):
    """Zwraca dict {ścieżka_pliku: [freecad_document, łączna_ilość]} dla wszystkich
    App::Link (i pochodnych, np. Assembly::AssemblyLink -- zob. niżej) w `doc` wskazujących
    na INNY, już zapisany dokument (linki wewnątrz tego samego dokumentu — np. wzorzec śrub
    w obrębie jednej części — są pomijane, bo nie mają osobnego pliku do wysłania). Ilość to
    suma po WSZYSTKICH linkach do tego samego pliku: zwykły (niearrayowy) link ma
    ElementCount=0, co liczymy jako 1 sztukę; wzorzec/tablica linków (ElementCount>0) liczy
    się jako tyle sztuk, ile wskazuje ElementCount.

    Sprawdzamy `isDerivedFrom("App::Link")`, NIE dokładne `TypeId == "App::Link"` -- natywny
    workbench Assembly reprezentuje niektóre komponenty (potwierdzone w praktyce: pod-złożenie
    wstawione jako komponent) jako `Assembly::AssemblyLink`, nie gołe `App::Link` -- dokładne
    porównanie TypeId cicho pomijało takie komponenty (nowo dodany element "znikał" z
    wykrywania drzewa, bez żadnego błędu), dokładnie tak jak `Part.export()` cicho pomijał
    ten sam typ obiektów przy eksporcie STEP (zob. `_upload_step_attachment`)."""
    result = {}
    App.Console.PrintMessage(f"EasyPDM: wykrywanie drzewa -- diagnostyka obiektow w '{doc.Name}':\n")
    for obj in doc.Objects:
        is_link = obj.isDerivedFrom("App::Link")
        if not is_link:
            App.Console.PrintMessage(f"  {obj.Name} ({obj.TypeId}): pomijam -- nie jest App::Link\n")
            continue
        linked = getattr(obj, "LinkedObject", None)
        if linked is None:
            App.Console.PrintMessage(f"  {obj.Name} ({obj.TypeId}): pomijam -- brak LinkedObject\n")
            continue
        # Link do zestawu zmiennych (App::VarSet) to WSPÓŁDZIELONE PARAMETRY, nie komponent
        # -- dwa dokumenty potrafią wskazywać nawzajem na swoje VarSet-y, co dawało dwa realne
        # błędy: w BOM powstawał CYKL (złożenie jako rodzic swojej własnej części, backend
        # słusznie odrzucał taką relację), a ilość sztuk komponentu była zawyżona o każdy taki
        # link. Potwierdzone w praktyce -- w Report View FreeCAD sam zgłaszał przy tym
        # "Document::getDependentDocuments: The graph must be a DAG."
        if linked.isDerivedFrom("App::VarSet"):
            App.Console.PrintMessage(
                f"  {obj.Name} ({obj.TypeId}): pomijam -- link do zestawu zmiennych (App::VarSet), nie do komponentu\n"
            )
            continue
        linked_doc = getattr(linked, "Document", None)
        if linked_doc is None:
            App.Console.PrintMessage(
                f"  {obj.Name} ({obj.TypeId}): pomijam -- LinkedObject '{linked.Name}' nie ma Document (dokument nieotwarty?)\n"
            )
            continue
        if not linked_doc.FileName:
            App.Console.PrintMessage(
                f"  {obj.Name} ({obj.TypeId}): pomijam -- dokument docelowy '{linked_doc.Name}' nie ma FileName (niezapisany)\n"
            )
            continue
        if linked_doc.FileName == doc.FileName:
            App.Console.PrintMessage(
                f"  {obj.Name} ({obj.TypeId}): pomijam -- link wewnatrz tego samego pliku\n"
            )
            continue
        App.Console.PrintMessage(f"  {obj.Name} ({obj.TypeId}): OK -- link do '{linked_doc.FileName}'\n")
        qty = getattr(obj, "ElementCount", 0) or 1
        qty = max(int(qty), 1)
        key = linked_doc.FileName
        if key not in result:
            result[key] = [linked_doc, 0]
        result[key][1] += qty
    return result


def discover_component_tree(top_doc):
    """Rekurencyjnie schodzi po App::Link dokumentu `top_doc` (i dalej w głąb, jeśli
    linkowany dokument sam ma dalsze linki). Zwraca:
        order — lista ścieżek plików odkrytych komponentów w kolejności "liście najpierw"
                (dzieci przed rodzicami), BEZ samego top_doc,
        docs  — dict {ścieżka_pliku: freecad_document} dla wszystkich odkrytych plików,
        edges — lista (ścieżka_rodzica, ścieżka_dziecka, ilość) dla WSZYSTKICH par
                rodzic-dziecko w drzewie, WŁĄCZNIE z tymi, gdzie rodzicem jest top_doc.
    `visited` chroni przed nieskończoną rekurencją, gdyby (nietypowo) powstał cykl."""
    order = []
    docs = {}
    edges = []
    visited = set()

    def visit(doc):
        if doc.FileName in visited:
            return
        visited.add(doc.FileName)
        for child_doc, qty in _iter_external_link_targets(doc).values():
            visit(child_doc)
            edges.append((doc.FileName, child_doc.FileName, qty))
        if doc.FileName != top_doc.FileName:
            docs[doc.FileName] = doc
            order.append(doc.FileName)

    visit(top_doc)
    return order, docs, edges


def match_existing_item(doc, existing_items):
    """Sprawdza, czy etykieta dokumentu wygląda jak "numer (nazwa).REWIZJA" — format,
    który to samo makro nadaje PO wysłaniu i od razu zapisuje na dysk (Save As pod nazwą
    PDM, zob. _rename_and_upload) — i jeśli tak, czy taki numer faktycznie istnieje w PDM.
    Zwraca dopasowany wpis (jak z GET /api/items) albo None, jeśli dokument trzeba dopiero
    utworzyć. Działa też w NOWEJ sesji FreeCAD, o ile otwarty zostanie przemianowany plik
    (ten pod nazwą PDM) — stara kopia sprzed wysyłki (zostawiona nietknięta na dysku, patrz
    _rename_and_upload) nadal ma oryginalną etykietę i nie zostanie rozpoznana.

    Samo dopasowanie numeru NIE wystarcza: użytkownik mógł nazywać swoje pliki wg
    WŁASNEJ konwencji "numer (nazwa)" jeszcze zanim kiedykolwiek użył tego makra — bez
    dodatkowego sprawdzenia nazwy makro po cichu podpięłoby dokument pod zupełnie
    NIEPOWIĄZANY, istniejący element PDM o tym samym numerze. Dlatego wymagamy zgodności
    OBU: numeru ORAZ nazwy (części w nawiasie) z fileName dopasowanego elementu."""
    m = _REVISION_NAME_PATTERN.match(doc.Label)
    if not m:
        return None
    item_number = int(m.group("number"))
    # Numer tylko zawęża wybór -- o trafieniu decyduje pełna nazwa rekordu, zob.
    # label_matches_item (sam numer łapał np. "testc2" jako element #2).
    for it in existing_items:
        if it.get("itemNumber") == item_number and label_matches_item(doc.Label, it):
            return it
    return None


def match_existing_item_single(doc):
    """Same check as match_existing_item, for a SINGLE document -- looks the parsed item
    number up directly via GET /items/by-number/{itemNumber} (the same targeted endpoint
    EasyPDM.SolidWorks/EasyPDM.Inventor use for their drawing-to-item matching) instead of
    downloading the WHOLE item table just to check one document's label. Only worth it here
    because there is exactly one document to check -- process_assembly_tree below still
    fetches the full list once and reuses it across all of an assembly's components, which
    stays cheaper than one targeted request per component for a non-trivial assembly."""
    m = _REVISION_NAME_PATTERN.match(doc.Label)
    if not m:
        return None
    item_number = int(m.group("number"))
    try:
        it = api_get(f"/items/by-number/{item_number}")
    except Exception:
        return None
    if it and label_matches_item(doc.Label, it):
        return it
    return None


# Materiał "Default" to to, co FreeCAD przypisuje bryle, której nikt nie nadał materiału --
# wysłanie go do PDM dałoby każdej części materiał "Default" i masę z przypadkowej gęstości.
_UNASSIGNED_MATERIAL_NAMES = {"", "default"}


def _final_solids(doc):
    """Widoczne, końcowe bryły części: obiekty z kształtem o niezerowej objętości, których nie
    zużywa żaden inny obiekt z kształtem. PartDesign Body zostaje, jego cechy (Pad, Pocket...)
    odpadają, bo wiszą pod Body; argumenty operacji Part (np. Cut) odpadają, bo zużywa je
    wynik operacji; szkice i elementy pomocnicze odpadają, bo nie mają objętości. Kontener
    App::Part nie jest obiektem z kształtem, więc bryły w nim zostają."""
    result = []
    for obj in doc.Objects:
        try:
            if not obj.isDerivedFrom("Part::Feature") or not getattr(obj, "Visibility", True):
                continue
            if any(p.isDerivedFrom("Part::Feature") for p in obj.InList):
                continue
            if obj.Shape.isNull() or obj.Shape.Volume <= 0:
                continue
            result.append(obj)
        except Exception:
            continue
    return result


def _material_density_kg_m3(material):
    """Gęstość materiału w kg/m^3 albo None. FreeCAD trzyma ją jako tekst z jednostką
    ("7900 kg/m^3"); przeliczenie robi jego własny system jednostek."""
    raw = None
    try:
        raw = material.getPhysicalValue("Density")
    except Exception:
        pass
    if raw is None:
        try:
            raw = (getattr(material, "PhysicalProperties", None) or {}).get("Density")
        except Exception:
            raw = None
    if raw is None or raw == "":
        return None
    try:
        q = App.Units.Quantity(raw) if isinstance(raw, str) else raw
        value = q.getValueAs("kg/m^3")
        value = float(getattr(value, "Value", value))
        return value if value > 0 else None
    except Exception:
        return None


def _insertable_object(doc):
    """Obiekt, który złożenie pokazuje przy wstawianiu tej części: jej jedyna końcowa bryła,
    a jeśli ta siedzi w kontenerze App::Part -- najbardziej zewnętrzny taki kontener (to on
    jest wtedy wstawiany). Kilka brył albo żadna -> None: nie ma jednego obiektu, który
    można by sensownie nazwać jak element w PDM."""
    solids = _final_solids(doc)
    if len(solids) != 1:
        return None
    obj = solids[0]
    try:
        parent = obj.getParentGeoFeatureGroup()
        while parent is not None:
            if parent.TypeId == "App::Part":
                obj = parent
            parent = parent.getParentGeoFeatureGroup()
    except Exception:
        pass
    return obj


def _label_main_object(doc, record_name):
    """Nadaje bryle części nazwę rekordu z PDM, BEZ rewizji -- np. "1(Cube)" przy pliku
    "1(Cube).A.FCStd".

    Złożenie (Assembly, App::Link) pokazuje przy wstawianiu etykiety obiektów, nie nazwę
    pliku, więc po samej zmianie nazwy pliku w oknie wstawiania dalej stało "Body" -- przy
    kilku częściach nie do odróżnienia (zgłoszone przez użytkownika). Rewizja zostaje tylko
    w nazwie pliku: etykieta bryły nie musiałaby się zmieniać przy każdej nowej rewizji.

    Tylko części: złożenie nie ma jednej bryły. Błąd niczego nie zatrzymuje -- to wygoda,
    nie warunek wysyłki."""
    try:
        if _cad_item_type(doc) != "part":
            return
        obj = _insertable_object(doc)
        if obj is not None and obj.Label != record_name:
            App.Console.PrintMessage(f"EasyPDM: etykieta '{obj.Label}' -> '{record_name}'\n")
            obj.Label = record_name
    except Exception as e:
        App.Console.PrintWarning(f"EasyPDM: nie udalo sie zmienic etykiety bryly: {e}\n")


def _component_record_name(linked_doc):
    """Nazwa rekordu PDM komponentu (bez rewizji) albo None, gdy plik nie jest z PDM.

    Plik wysłany przez to makro nazywa się "rekord.REWIZJA.FCStd", a etykieta dokumentu to
    ta sama nazwa bez rozszerzenia -- oba ustawia _rename_and_upload. Zgodność tych dwóch
    wystarcza, żeby rozpoznać plik z PDM bez pytania serwera: zwykły plik ("Plate.FCStd",
    etykieta "Plate") nie ma kropki z rewizją, a ręcznie zmieniona etykieta nie zgadza się z
    nazwą pliku."""
    try:
        base = os.path.splitext(os.path.basename(linked_doc.FileName or ""))[0]
    except Exception:
        return None
    if not base or base != linked_doc.Label or "." not in base:
        return None
    return base.rsplit(".", 1)[0]


def _label_links(doc):
    """Nadaje linkom złożenia nazwy komponentów z PDM, np. "2(Plate 1)" zamiast "Body001".

    Link ma WŁASNĄ etykietę, skopiowaną z obiektu w chwili wstawienia ("Body", a przy kolejnej
    części "Body001"). Późniejsza zmiana nazwy pliku i bryły komponentu (zob.
    _label_main_object) jej nie rusza, więc drzewo złożenia dalej pokazywało "Body", "Body001",
    "Zawartość"... mimo że linki wskazywały już właściwe pliki (zgłoszone przez użytkownika).

    Link zmienia nazwę tylko wtedy, gdy nie nosi już nazwy swojego komponentu -- także z
    końcówką, którą FreeCAD dokleja przy kilku egzemplarzach tej samej części
    ("2(Plate 1)001"), żeby kolejne wysyłki niczego nie przestawiały. Link do pliku spoza
    PDM zostaje bez zmian. Błąd tylko trafia do logu: to wygoda, nie warunek wysyłki."""
    for obj in doc.Objects:
        try:
            if not obj.isDerivedFrom("App::Link"):
                continue
            linked = getattr(obj, "LinkedObject", None)
            linked_doc = getattr(linked, "Document", None)
            if linked_doc is None or linked_doc is doc:
                continue
            record_name = _component_record_name(linked_doc)
            if record_name is None:
                continue
            label = obj.Label
            if label == record_name or (label.startswith(record_name) and label[len(record_name):].isdigit()):
                continue
            App.Console.PrintMessage(f"EasyPDM: link '{label}' -> '{record_name}'\n")
            obj.Label = record_name
        except Exception as e:
            App.Console.PrintWarning(f"EasyPDM: nie udalo sie zmienic etykiety linku: {e}\n")


def part_material_and_mass(doc):
    """(nazwa materiału albo None, masa w kg albo None) dla CZĘŚCI -- złożenia świadomie
    pomijamy (decyzja użytkownika: tylko części).

    Odpowiednik tego, co makra SolidWorks i Inventor biorą z programu. FreeCAD nie trzyma masy
    jako gotowej wartości, więc liczymy: objętość bryły (mm^3) x gęstość jej materiału, tak jak
    Inventor -- migawka z chwili wysyłki, po zmianie geometrii trzeba wysłać ponownie.

    Materiał: tylko gdy wszystkie końcowe bryły mają ten sam, nadany materiał.
    Masa: tylko gdy KAŻDA bryła ma materiał z gęstością -- suma z brakującymi bryłami byłaby
    zaniżona, a zaniżona masa w PDM jest gorsza niż żadna."""
    try:
        if _cad_item_type(doc) != "part":
            return None, None
        solids = _final_solids(doc)
        if not solids:
            return None, None
        names = set()
        mass = 0.0
        mass_complete = True
        for obj in solids:
            material = getattr(obj, "ShapeMaterial", None)
            name = (getattr(material, "Name", "") or "").strip()
            if name.lower() in _UNASSIGNED_MATERIAL_NAMES:
                names.add(None)
                mass_complete = False
                continue
            names.add(name)
            density = _material_density_kg_m3(material)
            if density is None:
                mass_complete = False
                continue
            mass += obj.Shape.Volume * 1e-9 * density
        material_name = next(iter(names)) if len(names) == 1 else None
        return material_name, (mass if mass_complete and mass > 0 else None)
    except Exception as e:
        App.Console.PrintMessage(f"EasyPDM: nie udalo sie odczytac materialu/masy: {e}\n")
        return None, None


def _mass_text(mass_kg):
    """Masa w kg jako tekst z kropką: 4 miejsca po przecinku, a dla bardzo małych części tyle
    cyfr znaczących, żeby nie wyszło "0"."""
    text = f"{mass_kg:.4f}".rstrip("0").rstrip(".")
    if text in ("", "0"):
        # Trzy cyfry znaczące, ale zapisane zwykłym ułamkiem ("0.0000158"), nie naukowo
        # ("1.58e-05") -- pole masy w PDM czytają ludzie i eksport BOM do CSV.
        from decimal import Decimal
        text = format(Decimal(f"{mass_kg:.3g}"), "f")
    return text


def _push_mass_and_material(doc, item_id):
    """Po wysyłce pliku zapisuje w elemencie PDM masę i materiał z modelu -- to samo, co robią
    makra SolidWorks i Inventor (PATCH /items/{id}/properties). Błąd tutaj nie psuje wysyłki:
    plik już jest w PDM, a wartości można wpisać ręcznie."""
    material, mass = part_material_and_mass(doc)
    fields = {}
    if mass is not None:
        fields["mass"] = _mass_text(mass)
    if material:
        fields["material"] = material
    if not fields:
        return
    try:
        api_patch_json(f"/items/{item_id}/properties", fields)
        App.Console.PrintMessage(f"EasyPDM: zapisano w PDM {fields}\n")
    except Exception as e:
        App.Console.PrintMessage(f"EasyPDM: nie udalo sie zapisac masy/materialu w PDM: {e}\n")


def _ask_sheet_on_page(doc, page):
    """Put the EasyPDM sheet on the document's ordinary TechDraw page? Asked on every upload
    until the page has the sheet -- a "No" clicked by mistake must not lock the sheet out for
    good, and once the sheet is there the question no longer comes up."""
    answer = QtWidgets.QMessageBox.question(
        None, t("pdm_title"), t("sheet_ask_existing_page", page=page.Label),
        QtWidgets.QMessageBox.Yes | QtWidgets.QMessageBox.No, QtWidgets.QMessageBox.Yes)
    return answer == QtWidgets.QMessageBox.Yes


def _refresh_drawing_sheet(doc, item_id):
    """Fills the EasyPDM sheet on the document's drawing pages before it is saved and sent, so
    the CAD file and the PDF in EasyPDM carry the current title block. A document without a
    drawing page is left alone. A failure here never stops the upload."""
    try:
        ask = (lambda page: _ask_sheet_on_page(doc, page)) if App.GuiUp else None
        changed = refresh_sheets(doc, item_id, ask)
        if changed:
            App.Console.PrintMessage("EasyPDM: drawing sheet refreshed on %s\n" % ", ".join(p.Label for p in changed))
    except Exception as e:
        App.Console.PrintMessage("EasyPDM: could not refresh the drawing sheet: %s\n" % e)


def _rename_and_upload(doc, item_id, record_name, name, revision, target_folder=None, export_step=True, export_pdf=False):
    """Wspólna końcówka obu trybów: KOPIUJE bieżący plik dokumentu do PDM pod nazwą
    "numer (nazwa).REWIZJA.rozszerzenie" (ta sama konwencja numer/nazwa co itemDisplayLabel
    we froncie, plus litera rewizji — zob. revision_label) — i teraz TAK SAMO zapisuje
    (Save As) LOKALNY dokument pod tą samą nazwą, w `target_folder` (jeśli podany — zob.
    TargetFolderDialog/run) albo domyślnie w tym samym folderze co oryginał.

    Po co zmieniać lokalny plik: jeśli ten dokument jest linkowany (App::Link) z jakiegoś
    ZŁOŻENIA otwartego w TEJ SAMEJ sesji FreeCAD, złożenie trzyma żywe odwołanie do obiektu
    Document, więc dalej "widzi" ten sam dokument mimo zmiany jego ścieżki — a gdy złożenie
    zostanie zapisane PO tej zmianie (co dla całego automatycznie wykrytego drzewa i tak
    następuje jako ostatni krok — to złożenie też przechodzi przez tę samą funkcję, patrz
    process_assembly_tree/run), zapisze swój odnośnik już pod NOWĄ nazwą (i w tym samym
    `target_folder`, jeśli wszystkie komponenty tam trafiają — dzięki temu odnośnik
    zapisany jako ścieżka względna nadal działa). Dzięki temu po pobraniu złożenia+
    składników przez EasyPDMDownload.FCMacro (który zapisuje pliki pod DOKŁADNIE tą samą
    konwencją nazw, do jednego wybranego folderu) odnośniki od razu się zgadzają — bez tego
    złożenie szukałoby oryginalnej, lokalnej nazwy pliku sprzed wysyłki, której pobieranie
    nigdy by nie odtworzyło (potwierdzone w praktyce: pobrane złożenie zgłaszało
    "Link broken! ... File: <oryginalna_nazwa>.FCStd"). STARY plik (pod oryginalną nazwą,
    w oryginalnym folderze) ZOSTAJE na dysku nietknięty — nic nie usuwamy automatycznie,
    tylko doc.FileName od teraz wskazuje na nowy.

    Plik zawsze trafia na serwer przez HTTP (POST .../attachments), pod tą samą, ładną nazwą.
    PDM ZACHOWUJE kopie poprzednich rewizji (np. "67 (nazwa).A.FCStd" zostaje, gdy powstaje
    rewizja B) -- zastępowana jest tylko kopia TEJ SAMEJ rewizji, czyli powtórna wysyłka bez
    zmiany statusu.

    Każdy załącznik dostaje rolę "cad" (patrz api_upload_file
    poniżej) — dzięki temu front pokazuje go osobno, pod "Załączniki CAD", zamiast razem
    ze zwykłymi, ręcznie dodanymi plikami. W odróżnieniu od ról "pdf"/"step" (jeden
    załącznik na rolę, nowy zastępuje poprzedni) rola "cad" może mieć wiele załączników —
    unikalna nazwa pliku per rewizja oznacza, że kolejne wysyłki się nie nadpisują.

    Zwraca dict: {"itemId", "itemNumber", "newPath", "localRenamed"} — "newPath" to ścieżka
    wysłanego lokalnego pliku (doc.FileName). "localRenamed" mówi, czy lokalny
    plik FAKTYCZNIE zmienił ścieżkę (False, jeśli już tam był — np. powtórna wysyłka tej samej
    rewizji już przemianowanego pliku) — do komunikatu końcowego w run(), żeby nie sugerować
    przenosin, które się nie odbyły."""
    ext = os.path.splitext(doc.FileName)[1]
    name_prefix = sanitize_filename(record_name)
    new_filename = f"{name_prefix}.{revision_label(revision)}{ext}"
    new_label = f"{record_name}.{revision_label(revision)}"
    new_local_path = os.path.join(target_folder or os.path.dirname(doc.FileName), new_filename)

    # KOLEJNOŚĆ JEST TU ISTOTNA: najpierw lokalny Save As pod nazwą PDM (razem z
    # odświeżeniem linków), DOPIERO POTEM kopia/wysyłka do PDM -- to, co idzie na serwer,
    # musi być plikiem JUŻ przemianowanym, z odniesieniami wskazującymi na nowe nazwy
    # komponentów. Wcześniej było odwrotnie (kopia szła pierwsza, "dopiero po potwierdzonym
    # sukcesie serwera" zmieniała się etykieta i lokalny plik) i to był realny błąd: do PDM
    # trafiał plik sprzed przemianowania, więc złożenie pobrane potem przez
    # EasyPDMDownload.FCMacro szukało komponentów pod ORYGINALNYMI nazwami sprzed wysyłki i
    # kończyło się serią "Link broken" (potwierdzone w praktyce na złożeniu, którego części
    # leżały na zupełnie innym dysku niż folder docelowy).
    #
    # Skutek uboczny zamiany: jeśli wysyłka padnie PO tym zapisie, lokalny plik zostaje już
    # pod nazwą PDM. To odwracalne i nieszkodliwe -- ponowne uruchomienie makra rozpozna go
    # po etykiecie (zob. match_existing_item) i zaproponuje dogranie do tego samego elementu.
    doc = _ensure_fully_loaded(doc)
    doc.Label = new_label
    _label_main_object(doc, record_name)
    _label_links(doc)
    # Mass and material first, then the drawing sheet: the title block shows the mass PDM
    # holds, so it has to be there before the sheet is filled and the file is saved and sent.
    _push_mass_and_material(doc, item_id)
    _refresh_drawing_sheet(doc, item_id)
    local_renamed = _save_local_as_pdm_name(doc, new_local_path)
    if local_renamed:
        _refresh_links_to(doc)

    # Zawsze przez HTTP. Kopiowanie wprost do magazynu serwera wymagałoby pewności, że klient
    # i serwer widzą ten sam dysk, a ścieżka z GET /api/config tego nie dowodzi: FreeCAD na
    # Windowsie przy serwerze w Dockerze potrafił założyć sobie lokalny C:\data\storage,
    # "skopiować" tam plik i dostać od serwera błąd rejestracji. Przy kolejnej wysyłce tej
    # samej rewizji było gorzej -- wpis już istniał, więc makro meldowało sukces, a na serwer
    # nic nie poszło. Serwer sam zastępuje wpis o tej samej nazwie, i to dopiero gdy ma już
    # nowy plik, więc nieudana wysyłka nie zabiera poprzedniej kopii tej rewizji.
    api_upload_file(
        f"/items/{item_id}/attachments", doc.FileName,
        override_filename=new_filename, extra_fields={"role": "cad"},
    )
    if export_step:
        _upload_step_attachment(doc, item_id)
    if export_pdf:
        _upload_pdf_attachment(doc, item_id)
    return {
        "itemId": item_id,
        "itemNumber": record_name,
        "newPath": doc.FileName,
        "localRenamed": local_renamed,
    }


def _refresh_links_to(changed_doc):
    """Po zmianie ścieżki pliku dokumentu (Save As pod nazwą PDM, zob. _save_local_as_pdm_name)
    wymusza odświeżenie WSZYSTKICH App::Link (w każdym innym otwartym dokumencie), które
    wskazują na TEN dokument -- przez ponowne przypisanie LinkedObject tą samą wartością.

    Po co: w pamięci link działa dalej bez żadnego odświeżania (trzyma żywe odwołanie do
    obiektu, nie do ścieżki), więc w tej samej sesji wszystko wygląda poprawnie. Ale zapisana
    NA DYSK referencja międzydokumentowa (App::PropertyXLink) potrafi zostać ze ścieżką z
    momentu, w którym link był USTAWIANY, zamiast odczytać aktualną przy zapisie -- efekt:
    złożenie zapisane po zmianie nazwy komponentu nadal ma w pliku STARĄ nazwę i po ponownym
    otwarciu (już w nowej sesji) zgłasza "Link broken" wskazując plik sprzed wysyłki, mimo że
    komponent leży obok pod nową nazwą (zgłoszone i potwierdzone w praktyce). Ponowne
    przypisanie tej samej wartości "dotyka" właściwość, więc najbliższy zapis dokumentu
    nadrzędnego serializuje już aktualną ścieżkę.

    Cicho ignoruje błędy pojedynczego obiektu/dokumentu -- to krok naprawczy, a nie warunek
    powodzenia wysyłki, która w tym momencie już się udała."""
    for other_doc in App.listDocuments().values():
        if other_doc is changed_doc:
            continue
        refreshed_any = False
        for obj in other_doc.Objects:
            try:
                if not obj.isDerivedFrom("App::Link"):
                    continue
                linked = getattr(obj, "LinkedObject", None)
                if linked is None or getattr(linked, "Document", None) is not changed_doc:
                    continue
            except Exception:
                continue
            # Przypisanie i touch w OSOBNYCH try -- LinkedObject bywa tylko do odczytu
            # (potwierdzone dla części typów pochodnych App::Link), a wtedy samo "touch"
            # nadal ma szansę wymusić ponowną serializację referencji.
            try:
                obj.LinkedObject = linked
            except Exception:
                pass
            try:
                obj.touch()
            except Exception:
                pass
            refreshed_any = True
            App.Console.PrintMessage(
                f"EasyPDM: odswiezono link '{other_doc.Name}.{obj.Name}' -> '{changed_doc.FileName}'\n"
            )
        # Bez jawnego oznaczenia dokumentu jako zmienionego jego save() na koncu run() bywa
        # pustym przebiegiem (FreeCAD pomija zapis dokumentu, ktory nie jest "touched") --
        # wlasnie dlatego zaktualizowana sciezka komponentu moglaby nigdy nie trafic na dysk.
        if refreshed_any:
            try:
                other_doc.recompute()
            except Exception:
                pass


def _ensure_fully_loaded(doc):
    """Dociąga dokument załadowany CZĘŚCIOWO (partial) do pełnego i zwraca dokument, na
    którym dalej należy pracować.

    FreeCAD ładuje dokument otwarty WYŁĄCZNIE jako zależność linku z innego dokumentu w
    trybie częściowym -- wczytuje tylko te obiekty, których wymagają same linki. Takiego
    dokumentu NIE DA SIĘ ZAPISAĆ: zapis kończy się cicho, a w Report View zostaje
    "Partial loaded document '<nazwa>' cannot be saved" (potwierdzone w praktyce: to był
    realny powód, dla którego komponent nigdy nie powstawał na dysku pod nazwą PDM, mimo
    że w pamięci wszystko wyglądało poprawnie). Dotyczy dokładnie typowego układu przy
    wysyłce złożenia: użytkownik otwiera samo złożenie, a jego części FreeCAD dociąga sam,
    właśnie częściowo.

    `App.openDocument` na już otwartym, częściowym dokumencie dociąga go do pełnego.
    Zwracamy to, co odda FreeCAD (a przy niepowodzeniu -- oryginalny obiekt), bo teoretycznie
    może to być inna instancja dokumentu niż przekazana."""
    file_name = getattr(doc, "FileName", "")
    if not file_name:
        return doc
    try:
        reloaded = App.openDocument(file_name)
        if reloaded is not None and reloaded is not doc:
            App.Console.PrintMessage(
                f"EasyPDM: dokument '{doc.Name}' byl zaladowany czesciowo -- dociagniety do pelnego\n"
            )
            return reloaded
    except Exception as e:
        App.Console.PrintMessage(f"EasyPDM: nie udalo sie dociagnac dokumentu '{doc.Name}': {e}\n")
    return doc


def _save_local_as_pdm_name(doc, new_local_path):
    """Save As lokalnego dokumentu pod nazwą PDM (numer/nazwa/rewizja), do new_local_path —
    patrz pełne wyjaśnienie w docstringu _rename_and_upload. Cicho ignoruje błąd zapisu (np.
    brak uprawnień, pełny dysk): sam upload do PDM już się powiódł w tym momencie, więc
    nieudana lokalna zmiana nazwy nie powinna wyglądać jak porażka całej operacji — w
    najgorszym razie lokalny plik zostaje pod starą nazwą, dokładnie jak przed tą funkcją.
    Zwraca True, jeśli plik faktycznie zmienił ścieżkę; False, jeśli już tam był (nic do
    zrobienia) albo zapis się nie udał.

    Sukces sprawdzamy po ISTNIENIU pliku, nie po braku wyjątku: zapis dokumentu załadowanego
    częściowo (zob. _ensure_fully_loaded) nie rzuca błędem, tylko cicho nic nie robi -- bez
    tej weryfikacji wracaliśmy stąd z True dla pliku, którego na dysku w ogóle nie ma."""
    if os.path.abspath(new_local_path) == os.path.abspath(doc.FileName):
        # Ta sama ścieżka (ponowna wysyłka już przemianowanego pliku) -- nie ma czego
        # przemianowywać, ale ZAPISAĆ trzeba: _rename_and_upload właśnie zmienił etykiety
        # (dokumentu, bryły, linków złożenia), a do PDM zaraz idzie kopia pliku Z DYSKU. Bez
        # tego zapisu w PDM lądowała wersja sprzed zmian -- po pobraniu złożenie znów miało
        # linki "Body", "Body001", choć lokalnie po wysyłce wszystko wyglądało dobrze
        # (zgłoszone przez użytkownika; lokalnie zapisywało się dopiero na końcu biegu).
        try:
            doc.recompute()
            doc.save()
        except Exception as e:
            App.Console.PrintMessage(f"EasyPDM: zapis '{new_local_path}' nie powiodl sie: {e}\n")
        return False
    try:
        doc.recompute()
        doc.saveAs(new_local_path)
    except Exception as e:
        App.Console.PrintMessage(f"EasyPDM: zapis '{new_local_path}' nie powiodl sie: {e}\n")
        return False
    if not os.path.exists(new_local_path):
        App.Console.PrintMessage(
            f"EasyPDM: zapis '{new_local_path}' nie utworzyl pliku (dokument zaladowany czesciowo?)\n"
        )
        return False
    return True


def _upload_step_attachment(doc, item_id):
    """Eksportuje widoczną geometrię `doc` do STEP i wgrywa jako załącznik z rolą "step" —
    zasila stały podgląd 3D w panelu elementu w aplikacji webowej (box 2D/3D nad
    Właściwościami, zob. ItemPreviewBox/RoleSlot). Zastępuje POPRZEDNI załącznik z tą rolą
    (usuwa go przed wysyłką nowego) — ta sama zasada "jeden plik na rolę" co przy ręcznym
    wgrywaniu przez slot STEP na stronie, więc podgląd zawsze pokazuje aktualną rewizję, nie
    starą.

    Błędy tutaj NIE przerywają wysyłki: sam upload/rejestracja pliku .FCStd (wywołujący tę
    funkcję z _rename_and_upload) już się w tym momencie powiodła — nieudany eksport STEP
    (np. dokument bez żadnej widocznej bryły — sam szkic, sam złom) nie powinien wyglądać
    jak porażka całej operacji."""
    try:
        import Part

        # doc.recompute() jest tu konieczny: dla złożeń (App::Link / kontenery zbierające
        # geometrię dzieci) .Shape bywa pustym, ale NIE-null compoundem, dopóki dokument
        # nie zostanie przeliczony na nowo -- taki obiekt przechodziłby filtr niżej
        # (isNull() == False) mimo że w środku nie ma ani jednej bryły/ściany, co dawało
        # STEP z samymi metadanymi produktu i zerową geometrią.
        try:
            doc.recompute()
        except Exception:
            pass

        def has_real_geometry(shape):
            return bool(shape.Solids or shape.Faces or shape.Edges)

        # Osie/płaszczyzny/punkty odniesienia (App::Origin/Line/Plane/Point) technicznie
        # maja niepusty Shape (cienka linia/plaszczyzna), ale to szum konstrukcyjny --
        # nigdy nie powinny trafic do eksportu.
        DATUM_PREFIXES = ("App::Origin", "App::Line", "App::Plane", "App::Point")
        # Kontenery, ktorych .Shape to juz gotowy, poprawnie ulozony compound WSZYSTKICH
        # swoich dzieci (zlozenie natywnego workbencha Assembly, albo App::Part) -- jesli
        # taki kontener jest obecny, bierzemy TYLKO jego, zeby nie zdublowac geometrii
        # dzieci (App::Link/Assembly::AssemblyLink) tez zebranych w petli nizej.
        CONTAINER_TYPES = ("Assembly::AssemblyObject", "App::Part", "PartDesign::Body")

        candidates = []
        App.Console.PrintMessage(f"EasyPDM: eksport STEP -- diagnostyka obiektow w '{doc.Name}':\n")
        for obj in doc.Objects:
            has_shape = hasattr(obj, "Shape")
            shape = obj.Shape if has_shape else None
            is_null = shape.isNull() if shape is not None else None
            has_geom = has_real_geometry(shape) if shape is not None and not is_null else False
            visible = getattr(obj, "Visibility", True)
            is_datum = obj.TypeId.startswith(DATUM_PREFIXES)
            App.Console.PrintMessage(
                f"  {obj.Name} ({obj.TypeId}): hasShape={has_shape} isNull={is_null} "
                f"hasGeometry={has_geom} visible={visible} datum={is_datum}\n"
            )
            if has_shape and shape is not None and not is_null and has_geom and visible and not is_datum:
                candidates.append(obj)

        # Kontenery typu Assembly::AssemblyObject/App::Part/PartDesign::Body agreguja we
        # wlasnym Shape geometrie wszystkich swoich dzieci (Linkow) juz poprawnie ulozona
        # wg polaczen/wiezow -- jesli taki kontener jest wsrod kandydatow, uzywamy TYLKO
        # jego (dzieci pomijamy, zeby nie zdublowac tej samej bryly w eksporcie).
        containers = [o for o in candidates if o.TypeId in CONTAINER_TYPES]
        chosen = containers if containers else candidates
        if not chosen:
            App.Console.PrintMessage("EasyPDM: eksport STEP -- brak obiektow z realna geometria, pomijam.\n")
            return

        shapes = [o.Shape for o in chosen]
        combined_shape = shapes[0] if len(shapes) == 1 else Part.makeCompound(shapes)

        tmp_dir = tempfile.mkdtemp(prefix="easypdm_step_")
        try:
            step_path = os.path.join(tmp_dir, sanitize_filename(doc.Label or "model") + ".step")
            # Eksport bezposrednio z gotowej bryly (combined_shape.exportStep), NIE przez
            # Part.export(objekty_dokumentu, ...) -- ta druga funkcja akceptuje do
            # eksportu tylko okreslone typy obiektow (np. Part::Feature) i po cichu
            # odrzuca Assembly::AssemblyObject/Assembly::AssemblyLink/App::Link z komunikatem
            # "is not a shape, export will be ignored", mimo ze maja poprawna geometrie --
            # to byla realna przyczyna pustych plikow STEP dla zlozen.
            combined_shape.exportStep(step_path)

            try:
                existing = api_get(f"/items/{item_id}/attachments") or []
            except Exception:
                existing = []
            for att in existing:
                if att.get("role") == "step":
                    try:
                        api_delete(f"/attachments/{att['id']}")
                    except Exception:
                        pass

            api_upload_file(
                f"/items/{item_id}/attachments", step_path,
                override_filename=os.path.basename(step_path),
                extra_fields={"role": "step"},
            )
        finally:
            shutil.rmtree(tmp_dir, ignore_errors=True)

        # Zrzut modelu idzie RAZEM ze STEP-em i tylko z nim: to on jest podglądem tego modelu
        # w aplikacji, a bez STEP-a nie miałby czego przedstawiać. Usunięcie STEP-a kasuje go
        # po stronie serwera (zob. MapDelete w AttachmentEndpoints.cs), więc nie zostają
        # sieroty. Wywoływane PO zamknięciu tmp_dir, bo zrzut ma własny katalog tymczasowy.
        _upload_model_image_attachment(doc, item_id)
    except Exception:
        pass


def _upload_model_image_attachment(doc, item_id):
    """Zapisuje widok modelu do PNG i wgrywa jako załącznik z rolą "image" — to JEST podgląd
    modelu pokazywany w aplikacji webowej.

    Wcześniej aplikacja renderowała w przeglądarce sam plik STEP (occt-import-js + three.js),
    żeby otrzymać NIERUCHOMY obraz: bez obracania, jedno renderer.render(). Cena była płacona
    przy KAŻDYM otwarciu elementu, u każdego użytkownika — pobranie bryły, teselacja przez
    OpenCascade w WebAssembly i liczenie krawędzi dla każdej bryły. Tutaj robi się to RAZ, na
    maszynie, która i tak ma model otwarty i policzony.

    Błędy nie przerywają niczego — tak samo jak w _upload_step_attachment: właściwy plik jest
    już w tym momencie wysłany, więc nieudany zrzut (np. FreeCAD uruchomiony bez GUI) nie
    powinien wyglądać jak porażka całej operacji. Każdy taki przypadek jest jednak WYPISYWANY
    do Report View: cicha porażka bez śladu kosztowała już jedno zgłoszenie "nie ma screenów",
    którego nie dało się zdiagnozować inaczej niż czytaniem kodu."""
    import FreeCADGui as Gui

    view = None
    created_view = False
    previous_document = None
    label = getattr(doc, "Label", "?")
    try:
        # Widok TEGO dokumentu, nie aktywnego. Gui.ActiveDocument to dokument, na którym
        # użytkownik akurat stoi — przy wysyłce złożenia jest nim złożenie, więc każdy
        # komponent dostawałby obraz złożenia zamiast własnego (tak właśnie zachowywał się
        # odpowiednik tej funkcji w SolidWorksie, zgłoszone z praktyki).
        try:
            view = _three_d_view_of(Gui.getDocument(doc.Name))
        except Exception as e:
            App.Console.PrintMessage(f"EasyPDM: zrzut '{label}' -- brak dokumentu GUI ({e})\n")

        if view is None:
            # Komponent złożenia zwykle NIE MA własnego okna 3D: FreeCAD wczytuje go jako
            # zależność linku z dokumentu nadrzędnego, do modelu w drzewie, ale bez okna.
            # Samo getDocument(...).ActiveView daje wtedy None, a zrzut po cichu nie powstaje
            # -- i dokładnie to się stało po przejściu z Gui.ActiveDocument na widok własny
            # dokumentu: złożenie (otwarte oknem) miało obrazek, żaden komponent nie miał.
            #
            # Okno 3D trzeba więc dla takiego dokumentu stworzyć, zrobić zrzut i je zamknąć.
            # Przełączenie aktywnego dokumentu jest tu nieuniknione (inaczej niż zakładał
            # komentarz, który tu wcześniej stał): to jedyna droga do widoku, z którego
            # saveImage w ogóle potrafi renderować.
            previous_document = getattr(getattr(Gui, "ActiveDocument", None), "Name", None)
            try:
                Gui.setActiveDocument(doc.Name)
                # activateView(typ, create=True) tworzy okno 3D, jeśli dokument go nie ma.
                Gui.activateView("Gui::View3DInventor", True)
                view = _three_d_view_of(Gui.ActiveDocument)
                created_view = view is not None
            except Exception as e:
                App.Console.PrintMessage(f"EasyPDM: zrzut '{label}' -- activateView nie zadzialalo ({e})\n")

        if view is None:
            App.Console.PrintMessage(
                f"EasyPDM: zrzut '{label}' pominiety -- nie udalo sie uzyskac widoku 3D tego dokumentu\n"
            )
            return

        # Ustawiony kadr: aksonometria i dopasowanie do okna. Bez tego zrzut pokazałby to, na
        # czym akurat stał użytkownik — zbliżenie na fragment albo widok z boku.
        #
        # viewAxonometric() i fitAll() wołane NA TYM widoku, a nie przez SendMsgToActiveView,
        # które trafiłoby w aktywny dokument i znów ustawiło kadr nie temu, komu trzeba.
        try:
            view.viewAxonometric()
            view.fitAll()
        except Exception:
            pass

        tmp_dir = tempfile.mkdtemp(prefix="easypdm_img_")
        try:
            image_path = os.path.join(tmp_dir, sanitize_filename(doc.Label or "model") + ".png")
            # Zrzut ma wyglądać tak samo niezależnie od tego, jakie tło robocze ma akurat
            # ustawione użytkownik (domyślnie FreeCAD daje gradient). saveImage przyjmuje tu
            # tylko nazwy: 'Current' | 'White' | 'Black' | 'Transparent' -- własnego koloru
            # (tego ciemnoszarego, co makra SolidWorks/Inventor) podać się nie da bez ruszania
            # globalnych ustawień FreeCAD-a, czego tu nie robimy.
            #
            # Dlatego 'Transparent', a nie 'Black': FreeCAD rysuje krawędzie modelu ciemnym
            # kolorem, więc na czarnym tle ginęłaby sylwetka części. Przezroczyste tło pokazuje
            # model na tle panelu aplikacji, cokolwiek nim jest -- krawędzie są widoczne
            # zarówno na jasnym, jak i na ciemnym motywie.
            view.saveImage(image_path, 1200, 900, "Transparent")
            if not os.path.exists(image_path):
                App.Console.PrintMessage(
                    f"EasyPDM: zrzut '{label}' pominiety -- saveImage nie utworzylo pliku\n"
                )
                return
            api_upload_file(
                f"/items/{item_id}/attachments", image_path,
                override_filename=os.path.basename(image_path),
                extra_fields={"role": "image"},
            )
            App.Console.PrintMessage(f"EasyPDM: zrzut '{label}' wyslany\n")
        finally:
            shutil.rmtree(tmp_dir, ignore_errors=True)
    except Exception as e:
        App.Console.PrintMessage(f"EasyPDM: zrzut '{label}' nie powiodl sie: {e}\n")
    finally:
        # Okno otwarte TYLKO po to, żeby zrobić zrzut, jest tu zamykane: przy złożeniu na
        # kilkanaście części zostałoby po wysyłce kilkanaście okien 3D, których użytkownik
        # nie otwierał. Zamknięcie jest najlepszym staraniem -- gdyby się nie udało, zostaje
        # otwarte okno, co jest brzydkie, ale niczego nie psuje.
        if created_view:
            try:
                view.close()
            except Exception as e:
                App.Console.PrintMessage(
                    f"EasyPDM: zrzut '{label}' -- nie udalo sie zamknac tymczasowego okna 3D ({e})\n"
                )
        if previous_document:
            try:
                Gui.setActiveDocument(previous_document)
            except Exception:
                pass


def _three_d_view_of(gui_doc):
    """Widok 3D dokumentu GUI, albo None gdy ten dokument nie ma własnego okna.

    Rozpoznawanie po obecności `saveImage`, a nie po typie: ActiveView dokumentu, na którym
    stoi strona TechDraw, jest widokiem RYSUNKU, nie 3D, i renderować się z niego nie da.
    `mdiViewsOfType` jest drugą szansą dla dokumentu, który okno 3D ma, ale aktywne jest w
    nim akurat inne."""
    if gui_doc is None:
        return None
    view = getattr(gui_doc, "ActiveView", None)
    if hasattr(view, "saveImage"):
        return view
    try:
        for candidate in gui_doc.mdiViewsOfType("Gui::View3DInventor"):
            if hasattr(candidate, "saveImage"):
                return candidate
    except Exception:
        pass
    return None


def _upload_pdf_attachment(doc, item_id):
    """Eksportuje `doc` do PDF i wgrywa jako załącznik z rolą "pdf" — analogicznie do
    _upload_step_attachment, ale niezależny wybór (checkbox w przeglądarce), nie powiązany
    z eksportem STEP. Ta sama zasada "jeden plik na rolę" (zastępuje poprzedni) i to samo
    tolerowanie błędów (upload dokumentu już się powiódł w tym momencie, nieudany eksport
    PDF nie powinien wyglądać jak porażka całej operacji).

    "Jeden plik na rolę" (nowy zastępuje poprzedni, także na dysku serwera) jest teraz
    wymuszane po stronie backendu (zob. ReplaceExistingRoleAttachmentAsync w
    AttachmentEndpoints.cs), więc -- w odróżnieniu od _upload_step_attachment powyżej --
    nie ma tu ręcznego pobierania/kasowania poprzedniego załącznika przed wysyłką.

    POTWIERDZONE na żywym FreeCAD: eksport surowych brył (bez strony TechDraw) do PDF
    faktycznie działa, ale gdy strona TechDraw JEST w dokumencie, samo podanie jej w liście
    obiektów do Gui.export() NIE WYSTARCZY -- musi być dodatkowo "aktywną stroną" FreeCAD
    (patrz doubleClicked() niżej), inaczej eksport cicho spada z powrotem do renderu 3D
    zamiast dać błąd. Stąd try/except obejmujący WSZYSTKO -- w najgorszym razie PDF po
    prostu nie powstanie, bez wpływu na resztę wysyłki."""
    try:
        import FreeCADGui as Gui

        # Prawdziwa strona TechDraw (rysunek techniczny) ma pierwszeństwo nad surowym
        # eksportem brył -- to jest właśnie ta "ugruntowana ścieżka" z komentarza wyżej.
        # Bierzemy pierwszą znalezioną (typowy dokument ma najwyżej jedną).
        techdraw_pages = [obj for obj in doc.Objects if obj.TypeId == "TechDraw::DrawPage"]
        previous_active_view = None
        if techdraw_pages:
            objs = [techdraw_pages[0]]
            # POTWIERDZONE NA ŻYWO: Gui.export() ze stroną TechDraw w liście obiektów
            # produkuje prawdziwy rysunek TYLKO gdy ta strona jest akurat "aktywną stroną"
            # FreeCAD (własne pojęcie TechDraw, powiązane z otwarciem jej zakładki widoku 2D)
            # -- z aktywną zakładką bryły PartDesign zamiast tego eksport CICHO spada z
            # powrotem do renderu 3D, bez żadnego błędu. doubleClicked() symuluje dokładnie
            # to kliknięcie strony w drzewie, które ręcznie naprawiało ten sam problem.
            # Zapamiętujemy poprzedni aktywny widok, żeby po eksporcie oddać użytkownikowi
            # dokładnie to, na czym pracował.
            try:
                previous_active_view = Gui.ActiveDocument.ActiveView
                objs[0].ViewObject.doubleClicked()
            except Exception:
                pass
        else:
            objs = [
                obj for obj in doc.Objects
                if hasattr(obj, "Shape") and obj.Shape and not obj.Shape.isNull()
                and getattr(obj, "Visibility", True)
            ]
        if not objs:
            return

        tmp_dir = tempfile.mkdtemp(prefix="easypdm_pdf_")
        try:
            pdf_path = os.path.join(tmp_dir, sanitize_filename(doc.Label or "model") + ".pdf")
            Gui.export(objs, pdf_path)
            if not os.path.exists(pdf_path):
                return

            api_upload_file(
                f"/items/{item_id}/attachments", pdf_path,
                override_filename=os.path.basename(pdf_path),
                extra_fields={"role": "pdf"},
            )
        finally:
            shutil.rmtree(tmp_dir, ignore_errors=True)
            if previous_active_view is not None:
                try:
                    Gui.ActiveDocument.ActiveView = previous_active_view
                except Exception:
                    pass
    except Exception:
        pass


def push_to_existing_item(doc, item_id, confirm_new_revision, target_folder=None, export_step=True, export_pdf=False):
    """Dogrywa bieżący dokument jako aktualny plik JUŻ ISTNIEJĄCEJ Części/Złożenia
    (np. nowa wersja po zmianach) — bez tworzenia nowego rekordu w PDM.

    Jeśli element ma status "wydany", w tym statusie nie da się dogrywać plików
    (backend blokuje to na wszelki wypadek, ale pytamy PRZED próbą, żeby nie kończyć się
    zwykłym błędem) — wywołuje `confirm_new_revision()` (funkcja bezargumentowa), pytając,
    czy stworzyć nową rewizję. Zwraca None, jeśli użytkownik odmówił — wtedy NIC nie jest
    zapisywane. W przeciwnym razie zwraca (możliwie pusty) tekst komentarza do rewizji.
    Status zmienia się na "w pracy" (PATCH /items/{id}/status — ten sam mechanizm co
    w aplikacji webowej, podnosi numer rewizji i opcjonalnie zapisuje komentarz), a dopiero
    potem plik trafia do PDM pod nazwą nowej rewizji."""
    if not doc.FileName:
        raise RuntimeError("Dokument nie jest zapisany na dysku.")
    doc.recompute()
    doc.save()

    item = api_get(f"/items/{item_id}")
    revision = item.get("revisionNumber") or 1
    current_status = item.get("status")
    # Serwer wysyła gotowe "isLocked" obok "status" (zob. ItemEndpoints.IsLocked -- ta sama
    # reguła, którą backend sam egzekwuje) -- wolimy je od odtwarzania "które statusy
    # blokują dogrywanie" lokalnie z surowego stringa, fallback na lokalne porównanie tylko
    # dla starszego serwera bez tego pola. "wydany" ma własną gałąź niżej niezależnie (jest
    # zablokowany też, ale oferuje nową rewizję zamiast twardej blokady).
    locked = item.get("isLocked")
    if locked is None:
        locked = current_status is not None and current_status != "w_pracy"

    if current_status == "wydany":
        comment = confirm_new_revision()
        if comment is None:
            return None
        status_result = api_patch_json(
            f"/items/{item_id}/status", {"status": "w_pracy", "comment": comment or None}
        )
        revision = (status_result or {}).get("revisionNumber") or (revision + 1)
        status_changed = True
    elif locked:
        # Każdy status poza "w_pracy" blokuje dogrywanie plików po stronie backendu
        # (zob. ItemEndpoints.IsLocked) — jedynym innym realnym stanem tutaj jest
        # "sprawdzany" ("wydany" ma własną gałąź wyżej). W przeciwieństwie do "wydany"
        # (gdzie powrót do "w_pracy" to świadoma, chciana akcja "nowa rewizja"),
        # "sprawdzany" oznacza, że ktoś aktywnie recenzuje ten element — cichy powrót do
        # "w_pracy" i wysłanie nowego pliku byłoby cichym skasowaniem recenzji w toku,
        # bez pytania kogokolwiek o zgodę. Zamiast tego twardo blokujemy z komunikatem —
        # to poprzednie zachowanie (cichy PATCH + wysyłka) było błędem.
        QtWidgets.QMessageBox.warning(
            None, t("pdm_title"), t("upload_blocked_review", number=item.get("itemNumber", item_id))
        )
        return None
    else:
        status_changed = False

    try:
        return _rename_and_upload(
            doc, item_id, record_name_text(item), item["fileName"], revision, target_folder, export_step, export_pdf
        )
    except Exception as exc:
        if status_changed:
            # Status/rewizja zostały już podniesione na serwerze (musiały być, żeby dogranie
            # pliku było w ogóle dozwolone) — skoro sama kopia/rejestracja pliku zawiodła,
            # element PDM jest teraz w rozjechanym stanie: nowa rewizja/status w bazie, ale
            # wciąż plik ze starej rewizji. Cofnięcie NIE jest tu bezpiecznie możliwe — backend
            # nie zezwala na przejście "w_pracy" -> "wydany" wprost (zob. isValidTransition
            # w ItemEndpoints.cs) — więc zamiast cichej/mylącej próby cofnięcia, głośno mówimy
            # dokładnie co się stało i co zrobić ręcznie.
            raise RuntimeError(
                t(
                    "status_revision_mismatch",
                    number=item.get("itemNumber"),
                    revision=revision,
                    error=exc,
                )
            ) from exc
        raise




class LoginDialog(QtWidgets.QDialog):
    """Logowanie do EasyPDM — pokazywane przez ensure_logged_in(), gdy nie ma jeszcze
    zapisanej sesji albo poprzednia wygasła/została unieważniona."""

    def __init__(self, parent=None):
        super().__init__(parent)
        self.setWindowTitle(t("login_dialog_title"))
        self.setMinimumWidth(360)

        layout = QtWidgets.QVBoxLayout(self)
        form = QtWidgets.QFormLayout()
        layout.addLayout(form)

        self.server_edit = QtWidgets.QLineEdit(get_base_url())
        form.addRow(t("api_address_label"), self.server_edit)

        self.username_edit = QtWidgets.QLineEdit()
        form.addRow(t("username_label"), self.username_edit)

        self.password_edit = QtWidgets.QLineEdit()
        self.password_edit.setEchoMode(QtWidgets.QLineEdit.Password)
        form.addRow(t("password_label"), self.password_edit)

        self.error_label = QtWidgets.QLabel("")
        self.error_label.setStyleSheet("color: #c0392b;")
        self.error_label.setWordWrap(True)
        layout.addWidget(self.error_label)

        buttons = QtWidgets.QDialogButtonBox(
            QtWidgets.QDialogButtonBox.Ok | QtWidgets.QDialogButtonBox.Cancel
        )
        buttons.button(QtWidgets.QDialogButtonBox.Ok).setText(t("login_button"))
        buttons.button(QtWidgets.QDialogButtonBox.Cancel).setText(t("cancel_button"))
        buttons.accepted.connect(self._try_login)
        buttons.rejected.connect(self.reject)
        layout.addWidget(buttons)

    def _try_login(self):
        self.error_label.setText("")
        set_base_url(self.server_edit.text().strip())
        username = self.username_edit.text().strip()
        password = self.password_edit.text()
        if not username or not password:
            self.error_label.setText(t("login_missing_fields"))
            return
        try:
            api_login(username, password)
        except Exception as e:
            self.error_label.setText(str(e))
            return
        self.accept()


class TargetFolderDialog(QtWidgets.QDialog):
    """Jedyne natywne okno z polami w całym przebiegu run() — pyta o folder, do
    którego mają trafiać lokalne kopie (Save As) wysyłanych dokumentów — pokazywane RAZ, na
    samym początku, PRZED jakimkolwiek przetwarzaniem (żeby objęło też automatycznie
    wykryte drzewo złożenia, wysyłane wcześniej niż cokolwiek innego). Ten sam folder co
    "Folder docelowy" w EasyPDMDownload.FCMacro (współdzielona preferencja DownloadFolder)
    — dzięki temu wysłane i pobrane pliki mogą lądować w tym samym, jednym miejscu. Trzyma
    też Adres API i informację o koncie (przeniesione tu z dawnego głównego okna "Wyślij do
    PDM", które już nie istnieje — wybór nowy/istniejący i wszystko dalsze dzieje się teraz
    w przeglądarce, zob. submit_via_browser) — to jedyne miejsce w całym przebiegu, gdzie
    można zmienić adres serwera albo się wylogować."""

    def __init__(self, doc, parent=None):
        super().__init__(parent)
        self.result_folder = None

        self.setWindowTitle(t("target_folder_dialog_title"))
        self.setMinimumWidth(440)

        layout = QtWidgets.QVBoxLayout(self)

        top_form = QtWidgets.QFormLayout()
        layout.addLayout(top_form)

        self.server_edit = QtWidgets.QLineEdit(get_base_url())
        top_form.addRow(t("api_address_label"), self.server_edit)

        account_row = QtWidgets.QHBoxLayout()
        self.account_label = QtWidgets.QLabel(t("logged_in_as", name=get_saved_username() or "?"))
        account_row.addWidget(self.account_label)
        logout_btn = QtWidgets.QPushButton(t("logout_button"))
        logout_btn.clicked.connect(self.on_logout)
        account_row.addWidget(logout_btn)
        account_row.addStretch(1)
        top_form.addRow(t("account_label"), account_row)

        layout.addWidget(QtWidgets.QLabel(t("target_folder_hint")))

        row = QtWidgets.QHBoxLayout()
        default_folder = get_download_folder() or (os.path.dirname(doc.FileName) if doc.FileName else "")
        self.folder_edit = QtWidgets.QLineEdit(default_folder)
        row.addWidget(self.folder_edit)
        browse_btn = QtWidgets.QPushButton("...")
        browse_btn.setMaximumWidth(32)
        browse_btn.clicked.connect(self.on_browse)
        row.addWidget(browse_btn)
        layout.addLayout(row)

        self.error_label = QtWidgets.QLabel("")
        self.error_label.setStyleSheet("color: #c0392b;")
        self.error_label.setWordWrap(True)
        layout.addWidget(self.error_label)

        buttons = QtWidgets.QDialogButtonBox(
            QtWidgets.QDialogButtonBox.Ok | QtWidgets.QDialogButtonBox.Cancel
        )
        buttons.accepted.connect(self._try_accept)
        buttons.rejected.connect(self.reject)
        layout.addWidget(buttons)

    def on_logout(self):
        api_logout()
        QtWidgets.QMessageBox.information(
            self, t("pdm_title"), t("logged_out_message")
        )
        self.reject()

    def on_browse(self):
        start = self.folder_edit.text().strip() or os.path.expanduser("~")
        chosen = QtWidgets.QFileDialog.getExistingDirectory(self, t("choose_target_folder_caption"), start)
        if chosen:
            self.folder_edit.setText(chosen)

    def _try_accept(self):
        set_base_url(self.server_edit.text().strip())
        folder = self.folder_edit.text().strip()
        if not folder:
            self.error_label.setText(t("indicate_folder"))
            return
        try:
            os.makedirs(folder, exist_ok=True)
        except OSError as e:
            self.error_label.setText(t("cannot_use_folder", error=e))
            return
        set_download_folder(folder)
        self.result_folder = folder
        self.accept()


def _main_window():
    """Główne okno FreeCAD jako rodzic dla pytań makra (None bez GUI)."""
    try:
        import FreeCADGui as Gui

        return Gui.getMainWindow()
    except Exception:
        return None


def _show_on_top(icon, title, text):
    """Komunikat, który wychodzi NA WIERZCH, także spod przeglądarki -- zob. tak samo nazwana
    funkcja w EasyPDMDownload.FCMacro. Błąd głównego pliku pada zaraz po wypełnieniu
    formularza, czyli gdy na wierzchu jest przeglądarka."""
    if sys.platform.startswith("linux"):
        _raise_via_kwin(_KWIN_FREECAD_MATCH % {"pid": os.getpid()})
    box = QtWidgets.QMessageBox(icon, title, text, QtWidgets.QMessageBox.Ok, _main_window())
    box.show()
    box.raise_()
    box.activateWindow()
    box.exec()


def _ask_yes_no(text, default_yes):
    """Pytanie Tak/Nie, które zawsze leży NAD oknem FreeCAD.

    QMessageBox.question(None, ...) tworzy osobne okno najwyższego poziomu, a KWin pod
    Waylandem (zgłoszone na CachyOS) potrafi położyć je POD głównym oknem FreeCAD, gdy to
    okno właśnie się aktywowało -- a tuż przed pytaniami o STEP/PDF makro zapisuje plik i
    robi zrzut modelu, co aktywuje widok 3D. Okno z rodzicem jest dla menedżera okien
    "przejściowe" (transient) i musi leżeć nad rodzicem, więc nie ma jak schować się pod
    spód; raise_/activateWindow dokładają jeszcze prośbę o fokus."""
    buttons = QtWidgets.QMessageBox.Yes | QtWidgets.QMessageBox.No
    box = QtWidgets.QMessageBox(QtWidgets.QMessageBox.Question, t("pdm_title"), text, buttons, _main_window())
    box.setDefaultButton(QtWidgets.QMessageBox.Yes if default_yes else QtWidgets.QMessageBox.No)
    box.show()
    box.raise_()
    box.activateWindow()
    return box.exec() == QtWidgets.QMessageBox.Yes


class NewRevisionDialog(QtWidgets.QDialog):
    """Pytanie o stworzenie nowej rewizji elementu o statusie "Wydany", z opcjonalnym
    komentarzem opisującym zmianę — ta sama treść, którą zapisuje aplikacja webowa."""

    def __init__(self, parent=None):
        super().__init__(parent)
        self.setWindowTitle(t("new_revision_title"))
        self.setMinimumWidth(380)

        layout = QtWidgets.QVBoxLayout(self)

        label = QtWidgets.QLabel(t("new_revision_body"))
        label.setWordWrap(True)
        layout.addWidget(label)

        layout.addWidget(QtWidgets.QLabel(t("revision_comment_label")))
        self.comment_edit = QtWidgets.QPlainTextEdit()
        self.comment_edit.setFixedHeight(70)
        self.comment_edit.setPlaceholderText(t("revision_comment_placeholder"))
        layout.addWidget(self.comment_edit)

        buttons = QtWidgets.QDialogButtonBox(
            QtWidgets.QDialogButtonBox.Ok | QtWidgets.QDialogButtonBox.Cancel
        )
        buttons.button(QtWidgets.QDialogButtonBox.Ok).setText(t("create_revision_button"))
        buttons.button(QtWidgets.QDialogButtonBox.Cancel).setText(t("cancel_button"))
        buttons.accepted.connect(self.accept)
        buttons.rejected.connect(self.reject)
        layout.addWidget(buttons)

    def comment_text(self):
        return self.comment_edit.toPlainText().strip()


def wait_for_ticket(ticket, timeout_seconds=600, raise_browser=False):
    """Czeka, aż formularz zostanie wypełniony w przeglądarce — BEZ własnego okna.

    Dotąd czekał na to modalny dialog „Czekam na przeglądarkę". Powstawał dokładnie w chwili,
    gdy przeglądarka dostała formularz i fokus — a nowe okno Qt zabierało fokus z powrotem,
    więc formularz lądował ZA FreeCAD-em i trzeba było w przeglądarkę kliknąć ręcznie.
    `WA_ShowWithoutActivating` tego nie powstrzymało (sprawdzone w praktyce, KDE/Wayland): o
    tym, czy nowe okno dostanie fokus, decyduje kompozytor, nie aplikacja.

    Makra SolidWorks i Inventor nie mają w tym miejscu żadnego okna — czekają, pisząc na
    pasku stanu. Tutaj jest teraz tak samo. Co się dzieje, widać w dwóch miejscach: na pasku
    stanu FreeCAD-a i w panelu postępu w przeglądarce, czyli tam, gdzie i tak się patrzy.

    Kosztem jest brak przycisku „Anuluj" — takiego samego, jakiego nigdy nie miały tamte dwa
    makra. Czekanie kończy się samo po `timeout_seconds`.

    Zwraca dane biletu albo None, gdy upłynął czas oczekiwania."""
    import time

    # Pasek stanu jest wygodą, nie częścią operacji: gdy nie da się go dosięgnąć (FreeCAD bez
    # GUI, inna wersja interfejsu), czekanie idzie dalej bez niego.
    status_bar = None
    try:
        import FreeCADGui as Gui

        status_bar = Gui.getMainWindow().statusBar()
        status_bar.showMessage(t("wait_ticket_status"))
    except Exception:
        status_bar = None

    try:
        deadline = time.time() + timeout_seconds
        polls = 0
        while time.time() < deadline:
            # Anulowane z przegladarki -- formularz i tak zniknal tam z ekranu, nie ma na co czekac.
            if transfer_cancelled():
                return None
            try:
                data = api_get(f"/create-tickets/{ticket}")
                if data and data.get("itemId"):
                    return data
            except Exception:
                # Chwilowy błąd sieci nie przerywa czekania — kolejny obieg spróbuje ponownie.
                pass

            # Przeglądarka otwarta przed chwilą przez open_in_browser: gdy już działała, nowa
            # karta mogła wylądować w tle (zob. _raise_via_kwin). Wyciągamy ją przy pierwszych
            # trzech odpytaniach — strona potrzebuje chwili, żeby załadować się i ustawić tytuł,
            # po którym okno jest rozpoznawane. Tylko trzy, żeby nie wyrywać fokusu komuś, kto
            # świadomie wrócił do FreeCAD-a.
            if raise_browser and polls < 3 and sys.platform.startswith("linux"):
                _focus_browser_window()
            polls += 1

            # Odpytujemy co 2 s, ale interfejs odświeżamy dziesięć razy częściej: bez tego
            # FreeCAD stałby zamrożony na cały czas czekania (dialog robił to za nas, mając
            # własną pętlę zdarzeń).
            for _ in range(20):
                try:
                    QtWidgets.QApplication.processEvents()
                except Exception:
                    pass
                time.sleep(0.1)

        App.Console.PrintMessage(f"EasyPDM: {t('wait_timeout')}\n")
        return None
    finally:
        if status_bar is not None:
            try:
                status_bar.clearMessage()
            except Exception:
                pass


def submit_via_browser(doc, target_folder):
    """Droga tworzenia nowego elementu ALBO dogrywania do istniejącego, gdy nie ma
    wystarczająco pewnego lokalnego dopasowania (zob. blok "already_linked" poniżej dla
    przypadku, gdy jest) — obie decyzje ("co", i "który") zapadają w przeglądarce, nie
    lokalnie (zob. build_browser_create_url). Makro: generuje bilet, otwiera przeglądarkę,
    czeka (wait_for_ticket). Po stronie przeglądarki dwie możliwe drogi dopełniają ten
    sam bilet: zwykłe "Dodaj" (nowy element, POST /nodes z ticketem) albo baner "oczekujące
    żądanie z makra" -> dogranie do istniejącego (POST /create-tickets/{ticket}/attach-
    existing) — GET /create-tickets/{ticket} zwraca pole "existing", które mówi, którą z
    dwóch dalszych ścieżek odpalić: dla nowego elementu wprost _rename_and_upload
    (rewizja=1); dla dogrania do istniejącego push_to_existing_item — ten ma WŁASNĄ,
    lokalną obsługę statusu "wydany" (pyta o nową rewizję i opcjonalny komentarz przez
    NewRevisionDialog) — to jedyna decyzja, która świadomie ZOSTAJE lokalna, bo jest
    bezpośrednio związana z tym, co makro zaraz zrobi z plikiem na dysku, a nie z
    właściwościami elementu w PDM.

    Czy eksportować STEP i/lub PDF wybiera się WYŁĄCZNIE w przeglądarce, jako dwa
    NIEZALEŻNE checkboxy widoczne w obu ścieżkach — makro nie ma tu żadnego lokalnego
    wyboru/fallbacku poza domyślnymi wartościami (STEP "tak", PDF "nie"), gdyby formularz
    z jakiegoś powodu nie przekazał wartości (starsza wersja frontendu).

    Zwraca to samo co _rename_and_upload/push_to_existing_item, albo None jeśli
    anulowano/upłynął czas oczekiwania — ten sam sygnał "nic nie zostało wysłane", który
    run() już rozumie."""
    matched = match_existing_item_single(doc)

    # Etykieta dokumentu wygląda jak "numer (nazwa).REWIZJA" i taki numer+nazwa istnieją w
    # PDM (zob. match_existing_item) -- pytamy WPROST, natywnie, czy podpiąć bieżącą wersję
    # jako nową rewizję TEGO elementu, zamiast po cichu zakładać "nowy" i zmuszać do ręcznego
    # znalezienia go przez wyszukiwarkę w przeglądarce (potwierdzone w praktyce: domyślny
    # wybór w przeglądarce to "Nowy element", więc bez tego pytania łatwo przeoczyć, że
    # dokument już istnieje, i utworzyć duplikat). Ten sam pomysł co natywna ścieżka
    # "already linked" w EasyPDMUpload.bas (SolidWorks), tam oparta o Custom Property
    # (pewny link) -- tutaj o dopasowanie etykiety (mniej pewne, stąd "Nie" tu NIE anuluje
    # całości, tylko spada do zwykłego formularza w przeglądarce poniżej, gdzie to samo
    # dopasowanie i tak zostaje podpowiedziane w wyszukiwarce "Dogranie do istniejącego").
    # Złożenie główne było już na liście "zaktualizować?" przy jego komponentach (zob.
    # process_assembly_tree) i odpowiedź brzmiała "tak" -- nie pytamy drugi raz ani o
    # podpięcie, ani o STEP/PDF.
    preset = _RUN.get("top_preset")
    if matched and preset and preset.get("item_id") != matched.get("id"):
        preset = None
    if matched:
        if preset or _ask_yes_no(
            t("already_linked_confirm", number=matched.get("itemNumber"), name=matched.get("fileName")),
            default_yes=True,
        ):
            def confirm_new_revision():
                dlg = NewRevisionDialog(_main_window())
                if dlg.exec() != QtWidgets.QDialog.Accepted:
                    return None
                return dlg.comment_text()

            # STEP/PDF export questions asked ONLY AFTER push_to_existing_item's own
            # status/revision gate has already passed -- it internally asks "create a new
            # revision?" for a "wydany" item (None back if declined) and hard-blocks
            # "sprawdzany" entirely (also None back). Asking export questions BEFORE that
            # (as this used to, passing native_export_step/pdf straight into the call)
            # risked the user answering "yes, export STEP" for an item whose revision they
            # then decline, or one that turns out blocked -- an answer to a question for an
            # operation that then never happens. export_step/export_pdf forced False here;
            # _upload_step_attachment/_upload_pdf_attachment are called directly below
            # instead, once we actually know the upload went through.
            result = push_to_existing_item(
                doc, matched["id"], confirm_new_revision,
                target_folder=target_folder, export_step=False, export_pdf=False,
            )
            if result is None:
                return None

            if preset["step"] if preset else _ask_yes_no(t("export_step_prompt"), default_yes=True):
                _upload_step_attachment(doc, matched["id"])
            if preset["pdf"] if preset else _ask_yes_no(t("export_pdf_prompt"), default_yes=False):
                _upload_pdf_attachment(doc, matched["id"])

            return result
        # "Nie" -- spada do zwykłego formularza w przeglądarce poniżej, z tym samym
        # dopasowaniem nadal podpowiedzianym tam (suggested_item_number), na wypadek gdyby
        # user jednak chciał wybrać "Dogranie do istniejącego" ręcznie.

    suggested_item_number = matched["itemNumber"] if matched else None

    ticket = str(uuid.uuid4())
    top_material = part_material_and_mass(doc)[0]
    # Po komponentach złożenia karta tego biegu już jest otwarta i właśnie podjęła ich
    # formularze -- główny dokument trafia do niej tak samo. Wcześniej szedł zawsze przez
    # nową kartę, więc po ostatnim komponencie wyskakiwała druga karta tylko po to, żeby
    # wypełnić formularz złożenia (zgłoszone przez użytkownika). Przy pojedynczym pliku
    # karty jeszcze nie ma i publish_cad_request od razu oddaje False.
    opened_tab = False
    if not publish_cad_request(ticket, doc.Label, _cad_item_type(doc), top_material, _document_size(doc),
                               suggested_item_number=suggested_item_number):
        try:
            url = build_browser_create_url(doc.Label, ticket, suggested_item_number, _document_size(doc), _cad_item_type(doc),
                                           material=top_material)
            open_in_browser(url)
            opened_tab = True
        except Exception as e:
            QtWidgets.QMessageBox.critical(None, t("pdm_title"), t("open_browser_failed", error=e))
            return None

    ticket_data = wait_for_ticket(ticket, raise_browser=opened_tab)
    if ticket_data is None:
        return None

    export_step = ticket_data.get("exportStep")
    if export_step is None:
        export_step = True
    export_pdf = ticket_data.get("exportPdf")
    if export_pdf is None:
        export_pdf = False

    if ticket_data.get("existing"):
        def confirm_new_revision():
            dlg = NewRevisionDialog(_main_window())
            if dlg.exec() != QtWidgets.QDialog.Accepted:
                return None
            return dlg.comment_text()

        return push_to_existing_item(
            doc, ticket_data["itemId"], confirm_new_revision,
            target_folder=target_folder, export_step=export_step, export_pdf=export_pdf,
        )

    return _rename_and_upload(
        doc, ticket_data["itemId"], record_name_text(ticket_data, ticket_data["name"]), ticket_data["name"],
        1, target_folder, export_step, export_pdf,
    )


def sync_stale_children(parent_item_id, local_child_ids):
    """Wykrywa dzieci elementu `parent_item_id`, które istnieją w PDM, ale NIE ma ich już
    wśród `local_child_ids` (odkrytych właśnie w lokalnej strukturze FreeCAD -- usunięte
    z drzewa złożenia od poprzedniej wysyłki). Makro dotąd tylko DODAWAŁ relacje BOM,
    nigdy nie usuwał tych, które zniknęły lokalnie -- potwierdzony w praktyce błąd:
    usunięcie komponentu ze złożenia w FreeCAD i ponowna wysyłka zostawiały starą relację
    w PDM nietkniętą. Przed usunięciem pyta natywnie o potwierdzenie (relacja mogła zostać
    dodana ręcznie w aplikacji webowej z innego powodu, niezwiązanego z tym plikiem
    FreeCAD) -- odmowa albo błąd pobrania listy NIC nie usuwa. Po każdym udanym usunięciu
    odpina usunięte dziecko od JAKIEGOKOLWIEK projektu (PATCH .../project {projectId:null})
    zamiast wrzucać je do korzenia bieżącego projektu -- element zostaje w pełni widoczny i
    znajdywalny przez globalne wyszukiwanie ("Cała baza"), tylko przestaje zaśmiecać
    strukturę projektu, z którym nie ma już nic wspólnego. Dokładnie ten sam mechanizm co
    ręczne "Usuń ze struktury" w aplikacji webowej."""
    try:
        existing_children = api_get(f"/items/{parent_item_id}/children") or []
    except Exception:
        return

    stale = []
    for entry in existing_children:
        child = entry.get("item", entry)
        child_id = child.get("id")
        if child_id and child_id not in local_child_ids:
            stale.append(child)

    if not stale:
        return

    lines = "\n".join(f"- {c.get('itemNumber')}({c.get('fileName')})" for c in stale)
    if not _ask_yes_no(t("stale_children_confirm", count=len(stale), lines=lines), default_yes=False):
        return

    for c in stale:
        try:
            api_delete(f"/items/{parent_item_id}/children/{c.get('id')}")
            api_patch_json(f"/items/{c.get('id')}/project", {"projectId": None})
        except Exception:
            pass


class AssemblyDetectedDialog(QtWidgets.QDialog):
    """Jedno okno decydujące o całym złożeniu: drzewo plików i Tak/Nie/Anuluj, a gdy w
    złożeniu są pliki już będące w PDM w pracy (do zaktualizowania) -- dodatkowo dwa pola
    STEP/PDF dla nich. Zastępuje ciąg osobnych okien "wysłać?", "zaktualizować?", "STEP?",
    "PDF?" (zgłoszone z praktyki: dwa okna pytały o to samo). Pola wyboru, a nie kolejne
    pytania Tak/Nie, bo QMessageBox ich nie ma -- stąd własne okno."""

    def __init__(self, body, show_update_options, parent=None):
        super().__init__(parent)
        self.setWindowTitle(t("assembly_detected_title"))
        self.setMinimumWidth(460)
        layout = QtWidgets.QVBoxLayout(self)

        label = QtWidgets.QLabel(body)
        label.setTextFormat(QtCore.Qt.PlainText)
        label.setWordWrap(True)
        # Długie złożenie nie może rozepchać okna poza ekran -- treść w przewijanym polu.
        scroll = QtWidgets.QScrollArea()
        scroll.setWidgetResizable(True)
        scroll.setFrameShape(QtWidgets.QFrame.NoFrame)
        scroll.setWidget(label)
        scroll.setMaximumHeight(420)
        layout.addWidget(scroll)

        self.step_box = self.pdf_box = None
        if show_update_options:
            self.step_box = QtWidgets.QCheckBox(t("update_step_checkbox"))
            self.step_box.setChecked(True)
            self.pdf_box = QtWidgets.QCheckBox(t("update_pdf_checkbox"))
            self.pdf_box.setChecked(False)
            layout.addWidget(self.step_box)
            layout.addWidget(self.pdf_box)

        buttons = QtWidgets.QDialogButtonBox()
        yes = buttons.addButton(t("yes_button"), QtWidgets.QDialogButtonBox.YesRole)
        no = buttons.addButton(t("no_button"), QtWidgets.QDialogButtonBox.NoRole)
        cancel = buttons.addButton(t("cancel_button"), QtWidgets.QDialogButtonBox.RejectRole)
        yes.setDefault(True)
        self.choice = "cancel"
        yes.clicked.connect(lambda: self._done("yes"))
        no.clicked.connect(lambda: self._done("no"))
        cancel.clicked.connect(lambda: self._done("cancel"))
        layout.addWidget(buttons)

    def _done(self, choice):
        self.choice = choice
        self.accept() if choice != "cancel" else self.reject()

    def export_step(self):
        return bool(self.step_box and self.step_box.isChecked())

    def export_pdf(self):
        return bool(self.pdf_box and self.pdf_box.isChecked())


def _tree_summary_lines(top_file, order, edges, make_line):
    """Lista do okna "Wykryto złożenie" ułożona w drzewo z wcięciami: złożenie główne, pod
    nim jego części i podzłożenia, pod podzłożeniem jego części -- o poziom głębiej każde.

    Ta sama zasada co w panelu postępu w przeglądarce (ProgressTree.cs): dzieci w kolejności
    z drzewa CAD, a część użyta w kilku złożeniach stoi pod KAŻDYM z nich (choć wysyłana jest
    raz). Plik nie może być własnym przodkiem -- to chroni przed cyklem. Komponent, do
    którego nie prowadzi żadna relacja (nie powinno się zdarzyć), trafia na koniec na
    pierwszy poziom, żeby nic nie zginęło z listy. make_line(ścieżka, głębokość, ilość)
    zwraca gotową linię."""
    children = {}
    for parent, child, qty in edges:
        children.setdefault(parent, []).append((child, qty))

    lines = [make_line(top_file, 0)]
    seen = {top_file}
    ancestors = [top_file]

    def place(parent, depth):
        for child, qty in children.get(parent, []):
            if child in ancestors:
                continue
            seen.add(child)
            lines.append(make_line(child, depth, qty))
            ancestors.append(child)
            place(child, depth + 1)
            ancestors.pop()

    place(top_file, 1)
    for f in order:
        if f not in seen:
            seen.add(f)
            lines.append(make_line(f, 1))
    return lines


def process_assembly_tree(top_doc, target_folder=None):
    """Wykrywa złożenie (App::Link do zewnętrznych plików, rekurencyjnie) i dla KAŻDEGO
    nowego komponentu (jeszcze nie wysłanego do PDM — rozpoznawane po etykiecie
    "numer (nazwa).REWIZJA", zob. match_existing_item) przechodzi przez TEN SAM bilet
    przeglądarki co główny dokument (zob. submit_via_browser) — jedna karta na raz, po
    kolei, w tej samej kolejności "liście najpierw" co reszta tego drzewa (nigdy kilka kart
    naraz — myląco się w tym gubić, a ochrona Windows przed "kradzieżą focusu" i tak
    wyciszyłaby każdą kolejną kartę otwartą zaraz po poprzedniej bez świeżej interakcji
    użytkownika, patrz notatka przed każdym otwarciem karty). Po utworzeniu/dograniu
    podpina relacje rodzic-dziecko (BOM) MIĘDZY odkrytymi komponentami.
    Relacje, gdzie rodzicem jest top_doc, NIE są tu podpinane — top_doc jeszcze nie ma
    swojego item_id w PDM (może to być nowy ALBO już istniejący element — o tym decyduje
    reszta run(), przez submit_via_browser); te relacje dopina run() po jego utworzeniu.

    Zwraca (edges_for_top, cancelled, locked_matches):
        edges_for_top   — lista (child_item_id, quantity, newly_created) do podpięcia pod
                          element top_doc (newly_created mówi run(), czy po podpięciu
                          trzeba ukryć ten element z korzenia projektu, zob. niżej),
        cancelled       — True, jeśli użytkownik przerwał w trakcie. Komponenty utworzone
                          PRZED przerwaniem zostają w PDM (tak samo jak reszta makra nie
                          cofa częściowo wykonanych kroków w razie błędu w połowie),
        locked_matches  — lista (itemNumber, fileName, status) dla już-podlinkowanych
                          komponentów (dopasowanych po etykiecie, patrz niżej) których
                          status to "sprawdzany"/"wydany" — takie komponenty są WYŁĄCZNIE
                          referencjonowane, nigdy nie próbujemy ich ponownie wysłać
                          niezależnie od statusu (drzewo złożenia w ogóle nie aktualizuje
                          już-istniejących komponentów, tylko podpina nowe) — ale run()
                          pokazuje tę listę w podsumowaniu na końcu, żeby było wiadomo,
                          które ewentualnie zmienione lokalnie części NIE zostały wysłane."""
    order, docs, edges = discover_component_tree(top_doc)
    if not order:
        return [], False, []

    try:
        existing_items = api_get("/items") or []
    except Exception as e:
        QtWidgets.QMessageBox.warning(None, t("pdm_title"), t("fetch_items_failed", error=e))
        existing_items = []

    # Pokazuje DOCELOWY numer/nazwę elementu dla każdego już rozpoznanego komponentu, nie
    # samą nazwę pliku -- jedyna szansa, żeby zauważyć nieaktualne dopasowanie, zanim
    # cokolwiek zostanie ruszone. match_existing_item dopasowuje po etykiecie dokumentu
    # ("numer (nazwa).REWIZJA"), a "Save As" w FreeCAD kopiuje etykietę razem z całą
    # resztą -- zapisanie od nowa, genuinie INNEJ części z takiej kopii sprawia, że makro
    # "rozpozna" ją jako STARY element, zamiast utworzyć nowy (potwierdzone w praktyce na
    # analogicznym mechanizmie w makrze SolidWorks -- tam przez Custom Property zamiast
    # etykiety, ale ryzyko jest identyczne).
    # Rozpoznanie każdego pliku RAZ, przed oknem: do dopisków na liście, do tego, czy
    # pokazać pola STEP/PDF, i do listy plików, których nie wyślemy.
    match_by_file = {f: match_existing_item(docs[f], existing_items) for f in order}
    top_match = match_existing_item(top_doc, existing_items)
    blocking = ("sprawdzany", "wydany")
    status_labels = {"sprawdzany": t("status_label_sprawdzany"), "wydany": t("status_label_wydany")}

    def summary_line(f, depth, qty=1):
        line = "    " * depth + f"- {os.path.basename(f)}"
        if qty > 1:
            line += f" ×{qty}"
        m = match_by_file.get(f)
        if m:
            line += t("already_in_pdm_as", number=m.get("itemNumber"), name=m.get("fileName"))
            if m.get("status") in blocking:
                line += t("not_sent_suffix", status=status_labels[m.get("status")])
        return line

    summary = "\n".join(_tree_summary_lines(getattr(top_doc, "FileName", ""), order, edges, summary_line))

    # Pliki już w PDM i w pracy -- przy "Tak" są aktualizowane bez dodatkowego pytania (plik
    # CAD zastępuje tę samą rewizję, serwer podmienia wpis o tej samej nazwie), a STEP/PDF
    # według pól w tym samym oknie. Dotąd były tylko podpinane do struktury, więc lokalne
    # zmiany w nich nie szły na serwer. Złożenie główne też, jeśli jest w pracy -- jego
    # decyzja trafia do _RUN["top_preset"], żeby submit_via_browser nie pytał drugi raz.
    updatable = [f for f in order if match_by_file[f] and match_by_file[f].get("status") not in blocking]
    top_updatable = bool(top_match) and top_match.get("status") not in blocking
    locked = [f for f in order if match_by_file[f] and match_by_file[f].get("status") in blocking]

    body = t("assembly_detected_body", count=len(order), summary=summary)
    if updatable or top_updatable:
        body += "\n\n" + t("assembly_update_note")
    dialog = AssemblyDetectedDialog(body, bool(updatable or top_updatable), _main_window())
    dialog.exec()
    if dialog.choice == "cancel":
        return [], True, []
    # "Nie" pomija tworzenie nowych komponentów i aktualizację istniejących -- już
    # podlinkowane i tak trafiają do struktury (podpięcie bez wysyłania pliku), dokładnie
    # ten sam podział co EasyPDM.SolidWorks/EasyPDMUpload.bas ProcessAssemblyTree.
    send_new_components = dialog.choice == "yes"
    update_existing = send_new_components and bool(updatable or top_updatable)
    update_step = dialog.export_step()
    update_pdf = dialog.export_pdf()
    if top_updatable and update_existing:
        _RUN["top_preset"] = {"item_id": top_match["id"], "step": update_step, "pdf": update_pdf}

    # Drugie okno tylko informuje -- wysłanie zablokowanych plików wymaga nowej rewizji albo
    # zdjęcia ze sprawdzania, czego makro samo nie zrobi. Pokazane tutaj, więc na końcu
    # biegu nie powtarzamy tej samej listy (zob. _RUN["locked_shown"] w run()).
    if send_new_components and locked:
        lines = "\n".join(
            f"- {os.path.basename(f)} — {status_labels[match_by_file[f].get('status')]}" for f in locked
        )
        QtWidgets.QMessageBox.information(_main_window(), t("pdm_title"), t("locked_not_sent", lines=lines))
        _RUN["locked_shown"] = True

    # Ścieżki UTWORZONE w tym biegu (w odróżnieniu od już-istniejących komponentów, tylko
    # podpinanych) -- gdy taki element zostanie podpięty pod swojego prawdziwego rodzica
    # poniżej, znika z korzenia projektu (show_in_tree=False). Nigdy nie był niezależnym
    # elementem -- jego utworzenie jest wyłącznie efektem ubocznym kolejności wysyłki
    # liście-najpierw (utwórz liść, POTEM podepnij go pod właściwego rodzica). Element JUŻ
    # podlinkowany to potencjalnie niezależny, celowo widoczny wpis katalogu -- podpięcie go
    # tutaj NIE może ruszać jego istniejącej widoczności na korzeniu (ta sama zasada co przy
    # ręcznym dodaniu istniejącego elementu do złożenia w aplikacji webowej).
    newly_created_paths = set()
    # Już-podlinkowane komponenty o zablokowanym statusie -- zbierane tu, pokazywane
    # dopiero w podsumowaniu na końcu run() (patrz docstring wyżej).
    locked_matches = []

    # Lista do panelu postępu w przeglądarce — zgłaszana TERAZ, bo dopiero teraz wiadomo, że
    # użytkownik potwierdził. Komponenty w kolejności wysyłki (liście najpierw), a na końcu
    # sam dokument nadrzędny, który leci po nich.
    # Pary rodzic-dziecko do ułożenia listy w drzewo. Rodzicem komponentów najwyższego poziomu
    # jest plik dokumentu nadrzędnego, który na liście stoi pod TOP_DOCUMENT_PROGRESS_KEY.
    top_file = getattr(top_doc, "FileName", "")
    progress_start("upload",
                   [(fp, progress_label_for(fp)) for fp in order]
                   + [(TOP_DOCUMENT_PROGRESS_KEY, progress_label_for(top_file))],
                   [(TOP_DOCUMENT_PROGRESS_KEY if parent == top_file else parent, child)
                    for parent, child, _qty in edges])
    # Poprzednia pozycja jest odhaczana na POCZĄTKU następnej, a ostatnia tuż za pętlą — ciało
    # pętli ma kilka ścieżek wyjścia (continue) i każda musiałaby inaczej o tym pamiętać.
    progress_prev = [None]

    doc_to_item_id = {}
    for file_path in order:
        if progress_prev[0]:
            progress_mark(progress_prev[0], "done")
        # Anulowanie z przeglądarki: stop PRZED kolejnym komponentem. Poprzedni jest już
        # wysłany i odhaczony linijkę wyżej; ten i następne zostają nieruszone.
        if transfer_cancelled():
            return [], True, locked_matches
        progress_mark(file_path, "active")
        progress_prev[0] = file_path
        doc = docs[file_path]
        matched = match_existing_item(doc, existing_items)
        if matched:
            doc_to_item_id[file_path] = matched["id"]
            matched_status = matched.get("status")
            if matched_status in ("sprawdzany", "wydany"):
                locked_matches.append((matched.get("itemNumber"), matched.get("fileName"), matched_status))
            elif update_existing:
                # Ta sama droga co ręczne dogranie do istniejącego elementu. Element jest
                # w pracy, więc pytania o nową rewizję nie będzie -- a gdyby status zdążył się
                # zmienić, push_to_existing_item zwraca None i komponent zostaje tylko
                # podpięty. Błąd jednego komponentu nie przerywa biegu: reszta złożenia
                # i tak ma pójść, a ten plik dostaje w panelu czerwony krzyżyk.
                try:
                    push_to_existing_item(
                        doc, matched["id"], lambda: None,
                        target_folder=target_folder, export_step=update_step, export_pdf=update_pdf,
                    )
                except Exception as e:
                    progress_mark(file_path, "failed")
                    progress_prev[0] = None
                    QtWidgets.QMessageBox.warning(
                        _main_window(), t("pdm_title"),
                        t("upload_component_failed", file=os.path.basename(file_path), error=e),
                    )
        elif not send_new_components:
            # Nie tworzymy nowych komponentów w tym biegu ("No" wyżej) -- pomiń, bez dodania
            # do doc_to_item_id. Każda relacja z udziałem tego pliku (jako rodzic lub
            # dziecko) zostanie naturalnie pominięta niżej (child_item_id is None / plik nie
            # w doc_to_item_id) zamiast rzucić błędem.
            continue
        else:
            # Ten sam bilet przeglądarki co główny dokument (submit_via_browser) --
            # otwierany JEDEN NA RAZ. Natywny popup tuż przed każdym otwarciem karty:
            # ochrona Windows przed "kradzieżą focusu" przepuszcza tylko PIERWSZE
            # programowe otwarcie przeglądarki w danym biegu, każde kolejne bez świeżej
            # interakcji użytkownika ląduje bez focusu (potwierdzone w praktyce na
            # analogicznym mechanizmie w makrze SolidWorks) -- kliknięcie OK tutaj liczy
            # się jako świeża interakcja.
            suggested_name = doc.Label
            ticket = str(uuid.uuid4())

            # Najpierw zostawiamy prośbę już otwartej karcie. Nowa karta — i okno, które
            # przywraca możliwość przejęcia fokusu — tylko wtedy, gdy nikt jej nie podjął,
            # czyli gdy przeglądarka jest zamknięta.
            opened_tab = False
            component_material = part_material_and_mass(doc)[0]
            if not publish_cad_request(ticket, suggested_name, _cad_item_type(doc),
                                       component_material, _document_size(doc), component=True):
                # Okno TYLKO wtedy, gdy karta tego biegu już raz powstała. PIERWSZE otwarcie
                # przeglądarki w biegu i tak przejmuje fokus (to ta reguła Windows kazała klikać
                # OK przed KOLEJNYMI), więc dla pierwszego komponentu jest zbędne — a to on
                # otwiera kartę, która obsłuży resztę bez kart i okien.
                if _RUN["tab_opened"]:
                    QtWidgets.QMessageBox.information(
                        None, t("pdm_title"), t("new_component_browser_prompt", name=suggested_name)
                    )
                try:
                    url = build_browser_create_url(suggested_name, ticket, None, _document_size(doc), _cad_item_type(doc), component=True,
                                                   material=component_material)
                    open_in_browser(url)
                    opened_tab = True
                except Exception as e:
                    QtWidgets.QMessageBox.critical(None, t("pdm_title"), t("open_browser_failed", error=e))
                    return [], True, locked_matches

            ticket_data = wait_for_ticket(ticket, raise_browser=opened_tab)
            if ticket_data is None:
                return [], True, locked_matches

            comp_export_step = ticket_data.get("exportStep")
            if comp_export_step is None:
                comp_export_step = True
            comp_export_pdf = ticket_data.get("exportPdf")
            if comp_export_pdf is None:
                comp_export_pdf = False

            try:
                if ticket_data.get("existing"):
                    def confirm_new_revision():
                        rev_dlg = NewRevisionDialog(_main_window())
                        if rev_dlg.exec() != QtWidgets.QDialog.Accepted:
                            return None
                        return rev_dlg.comment_text()

                    result = push_to_existing_item(
                        doc, ticket_data["itemId"], confirm_new_revision,
                        target_folder=target_folder, export_step=comp_export_step, export_pdf=comp_export_pdf,
                    )
                    if result is None:
                        # Albo element już istniejący jest "wydany" i użytkownik odmówił
                        # nowej rewizji, albo ma status "sprawdzany" i push_to_existing_item
                        # zablokował wysyłkę z własnym komunikatem -- w obu przypadkach
                        # traktujemy jak każdą inną rezygnację w tej pętli.
                        return [], True, locked_matches
                else:
                    # Nowy element -- już istnieje po stronie serwera (przeglądarka
                    # wywołała POST /nodes z tym biletem), więc kończymy WPROST wysyłką
                    # pliku; tworzenie kolejnego elementu przez API stworzyłoby DRUGI
                    # rekord.
                    result = _rename_and_upload(
                        doc, ticket_data["itemId"], record_name_text(ticket_data, ticket_data["name"]), ticket_data["name"],
                        1, target_folder, comp_export_step, comp_export_pdf,
                    )
                    newly_created_paths.add(file_path)
            except Exception as e:
                QtWidgets.QMessageBox.critical(
                    None, t("pdm_title"), t("upload_component_failed", file=os.path.basename(file_path), error=e)
                )
                return [], True, locked_matches
            doc_to_item_id[file_path] = result["itemId"]

        # Zanim dogramy AKTUALNE relacje niżej, sprawdź czy w PDM nie zostały jakieś
        # relacje do dzieci, których już nie ma w lokalnej strukturze tego pod-złożenia
        # (usunięte z drzewa FreeCAD od poprzedniej wysyłki) -- zob. sync_stale_children.
        local_child_ids_here = {
            doc_to_item_id[cf] for pf, cf, _ in edges if pf == file_path and cf in doc_to_item_id
        }
        sync_stale_children(doc_to_item_id[file_path], local_child_ids_here)

        # Podpinamy relacje TERAZ, w TEJ SAMEJ iteracji w której file_path (jako rodzic)
        # właśnie dostał swoje item_id — NIE w osobnej pętli po całkowitym zakończeniu
        # tworzenia wszystkich komponentów. "order" gwarantuje dzieci przed rodzicami
        # (zob. discover_component_tree), więc każde dziecko z "edges" ma tu już swoje
        # item_id. Dzięki temu przerwanie w połowie (return wyżej, przy kolejnym pliku)
        # zostawia już utworzone komponenty PRAWIDŁOWO POWIĄZANE między sobą, zamiast
        # (jak wcześniej) kompletnie osieroconymi, bez żadnej struktury BOM.
        for parent_file, child_file, qty in edges:
            if parent_file != file_path:
                continue
            child_item_id = doc_to_item_id.get(child_file)
            if child_item_id is None:
                continue
            try:
                api_post_json(
                    f"/items/{doc_to_item_id[file_path]}/children",
                    {"childId": child_item_id, "quantity": qty},
                )
            except Exception as e:
                QtWidgets.QMessageBox.warning(
                    None,
                    t("pdm_title"),
                    t(
                        "link_child_failed",
                        child=os.path.basename(child_file),
                        parent=os.path.basename(parent_file),
                        error=e,
                    ),
                )
                continue

            if child_file in newly_created_paths:
                # Teraz prawidłowo zagnieżdżony pod swoim prawdziwym rodzicem -- ukryj go
                # z korzenia projektu (zob. komentarz przy newly_created_paths wyżej).
                try:
                    api_patch_json(f"/items/{child_item_id}/visibility", {"showInTree": False})
                except Exception:
                    pass

    # Ostatni komponent nie ma już następnego, który by go odhaczył.
    if progress_prev[0]:
        progress_mark(progress_prev[0], "done")

    # Relacje, w których rodzicem jest top_doc SAMO W SOBIE, nie mogły zostać podpięte
    # w pętli powyżej (top_doc celowo nie jest częścią "order" — nie ma jeszcze własnego
    # item_id, o tym decyduje reszta run()) — zwracamy je do podpięcia przez wywołującego.
    edges_for_top = [
        (doc_to_item_id[child_file], qty, child_file in newly_created_paths)
        for parent_file, child_file, qty in edges
        if parent_file == top_doc.FileName and child_file in doc_to_item_id
    ]

    return edges_for_top, False, locked_matches


def run():
    # Krok 0: upewnij się, że jest aktywna sesja — EasyPDM.Api wymaga jej dla każdego
    # wywołania poza samym logowaniem.
    if not ensure_logged_in():
        return  # użytkownik anulował logowanie

    doc = App.ActiveDocument
    if doc is None:
        QtWidgets.QMessageBox.warning(None, t("pdm_title"), t("no_active_document"))
        return

    # Krok 1: zapisz element przed wrzuceniem do PDM.
    if not doc.FileName:
        QtWidgets.QMessageBox.information(
            None, t("pdm_title"), t("document_not_saved")
        )
        import FreeCADGui as Gui

        Gui.runCommand("Std_SaveAs")
        if not doc.FileName:
            return  # użytkownik anulował zapis
    else:
        try:
            # recompute PRZED save — bez tego (potwierdzone w praktyce: gwiazdka "niezapisane
            # zmiany" pojawiała się natychmiast po tym save, jeszcze przed oknem folderu)
            # save łapie dokument PRZED ustabilizowaniem się solvera złączeń workbencha
            # Assembly, więc plik od razu po zapisie znów wygląda na "dotknięty".
            doc.recompute()
            doc.save()
        except Exception as e:
            QtWidgets.QMessageBox.critical(None, t("pdm_title"), t("save_failed", error=e))
            return

    # Krok 1a-0: folder docelowy dla lokalnych kopii (Save As) — pytamy RAZ, na samym
    # początku, przed process_assembly_tree (które dla automatycznie wykrytego drzewa i tak
    # wysyła części WCZEŚNIEJ niż otworzy się główne okno) — dzięki temu wszystkie
    # komponenty (części + finalne złożenie) lądują w TYM SAMYM, jednym folderze.
    folder_dialog = TargetFolderDialog(doc)
    if folder_dialog.exec() != QtWidgets.QDialog.Accepted:
        return
    target_folder = folder_dialog.result_folder

    # Od tego miejsca pliki na dysku mogą już zmieniać nazwy (Save As komponentów w
    # process_assembly_tree), więc zwykły zapis na koniec musi przyjść NIEZALEŻNIE od tego,
    # jak bieg się skończy -- także po anulowaniu w przeglądarce, odmowie nowej rewizji albo
    # wyjątku w połowie. Wcześniej był tylko na końcu udanej ścieżki: złożenie w pamięci
    # wskazywało już nowe nazwy części, a plik na dysku stare, aż do ręcznego Ctrl+S.
    #
    # Błąd głównego pliku (albo nieprzewidziany w innym miejscu) kończy bieg tutaj. Bez tego
    # bieg nie był zamykany: panel w przeglądarce kręcił się dalej przy pliku, którego już nikt
    # nie wysyłał, raport nie powstawał, a sam błąd lądował tylko w Report View. Okno dopiero po
    # zapisie, żeby zapis nie czekał, aż ktoś je zamknie.
    failure = None
    try:
        _send_and_link(doc, target_folder)
    except Exception as e:
        failure = e
        import traceback

        App.Console.PrintError("EasyPDM: " + traceback.format_exc() + "\n")
        progress_mark(TOP_DOCUMENT_PROGRESS_KEY, "failed")
        progress_finish()
    finally:
        _save_open_documents()

    if failure is not None:
        _show_on_top(
            QtWidgets.QMessageBox.Critical, t("pdm_title"),
            t("upload_component_failed", file=os.path.basename(doc.FileName), error=failure),
        )


def _save_open_documents():
    """Zwykły zapis (nie Save As) wszystkich otwartych, zapisanych już na dysku dokumentów:
    złożenia i każdej Części/pod-złożenia otwartego w tej sesji przez process_assembly_tree.

    Wszystkie, a nie tylko top_doc: FreeCAD potrafi oznaczyć dokument jako zmieniony
    ("gwiazdka") dopiero PO naszym Save As -- solver złożeń workbencha Assembly i
    aktualizacja ścieżek w App::Link dzieją się przy recompute, więc samo recompute
    top_doc w praktyce nie wystarczało (potwierdzone przez użytkownika). Z tego samego
    powodu zapis jest powtarzany: pierwsze przejście zapisuje WSZYSTKIE dokumenty bez
    pytania o flagę zmian (tak jak dotąd -- gdyby flaga kiedyś skłamała, nie tracimy zapisu,
    który działał), kolejne dwa już tylko te, które FreeCAD nadal oznacza jako zmienione,
    bo pierwszy zapis potrafi sam wywołać kolejne "dotknięcie".

    Błąd zapisu jednego dokumentu nie blokuje pozostałych, ale już NIE jest połykany po
    cichu: lista nieudanych ląduje w Report View i w oknie, bo bez tego lokalny plik
    zostaje z odwołaniami do starych nazw, a nikt się o tym nie dowiaduje."""
    import FreeCADGui as Gui

    def is_modified(d):
        gui_doc = Gui.getDocument(d.Name) if App.GuiUp else None
        return bool(getattr(gui_doc, "Modified", True))

    failed = {}
    for attempt in range(3):
        pending = [
            d for d in App.listDocuments().values() if d.FileName and (attempt == 0 or is_modified(d))
        ]
        if not pending:
            break
        for d in pending:
            try:
                d.recompute()
                d.save()
                failed.pop(d.FileName, None)
            except Exception as e:
                failed[d.FileName] = str(e)
                App.Console.PrintMessage(f"EasyPDM: zapis '{d.FileName}' nie powiodl sie: {e}\n")

    if failed:
        lines = "\n".join(f"- {os.path.basename(path)}: {err}" for path, err in failed.items())
        QtWidgets.QMessageBox.warning(None, t("pdm_title"), t("final_save_failed", lines=lines))


def _send_and_link(doc, target_folder):
    """Właściwa wysyłka: drzewo złożenia, dokument główny i relacje BOM. Wydzielone z run(),
    żeby run() mógł objąć ją try/finally z zapisem lokalnych plików na końcu."""
    # Eksport STEP/PDF nie jest już nigdzie wyborem w samym makrze -- decydują o tym dwa
    # niezależne checkboxy w przeglądarce, ZA KAŻDYM RAZEM gdy przeglądarka pośredniczy:
    # dla głównego dokumentu (Krok 2 niżej) i, od teraz, TAKŻE dla każdego automatycznie
    # wykrytego nowego komponentu złożenia z osobna (zob. process_assembly_tree) -- każdy
    # dostaje WŁASNY bilet, więc własny wybór, nie jeden odgórny dla całego drzewa.
    #
    # Krok 1a: wykryj i (opcjonalnie) wyślij złożenie rekurencyjnie — części/pod-złożenia
    # znalezione przez App::Link, w kolejności liście-najpierw.
    edges_for_top, cancelled, locked_matches = process_assembly_tree(doc, target_folder)
    if cancelled:
        # Bieg trzeba zamknąć także tu, nie tylko po udanej wysyłce: bez tego panel postępu
        # w przeglądarce wisiał do wygaśnięcia, a raport z biegu nigdy nie powstawał.
        progress_finish()
        # Po „Anuluj" w przeglądarce okno jest zbędne — raport idzie do powiadomień, tam,
        # gdzie kliknięto.
        if not _RUN["cancelled"]:
            QtWidgets.QMessageBox.information(None, t("pdm_title"), t("cancelled_upload"))
        return

    # Pojedyncza część (albo złożenie bez komponentów) nie przeszła przez drzewo, więc lista
    # postępu jeszcze nie istnieje -- bez tego panel w przeglądarce w ogóle się nie pokazywał
    # (zgłoszone z praktyki), a odhaczenie dokumentu na końcu trafiało w nicość. Jedna pozycja
    # wystarczy: ten sam panel, ten sam raport w powiadomieniach co przy złożeniu.
    if not _RUN["progress_started"]:
        progress_start("upload", [(TOP_DOCUMENT_PROGRESS_KEY, progress_label_for(getattr(doc, "FileName", "")))])
    progress_mark(TOP_DOCUMENT_PROGRESS_KEY, "active")

    # Krok 2: nowy element czy dogranie do istniejącego? Makro już o to w ogóle nie pyta —
    # ta decyzja, razem z wyborem CO/KTÓRY, zapada w przeglądarce (zob. submit_via_browser).
    info = submit_via_browser(doc, target_folder)

    if info is None:
        # Anulowano/upłynął czas oczekiwania na przeglądarkę, element był "Wydany" i
        # użytkownik odmówił stworzenia nowej rewizji, albo element ma status "Sprawdzany"
        # i push_to_existing_item już pokazał własny komunikat blokujący — w każdym z tych
        # przypadków nic nie wysłano.
        progress_finish()
        # „Nic nie wysłano" byłoby po anulowaniu z przeglądarki nieprawdą — komponenty mogły
        # już pójść — a raport z biegu i tak trafia do powiadomień.
        if not _RUN["cancelled"]:
            QtWidgets.QMessageBox.information(None, t("pdm_title"), t("nothing_sent"))
        return

    # Zanim dogramy AKTUALNE relacje niżej, sprawdź czy w PDM nie zostały jakieś relacje
    # do dzieci, których już nie ma w lokalnej strukturze złożenia (usunięte z drzewa
    # FreeCAD od poprzedniej wysyłki) -- zob. sync_stale_children.
    sync_stale_children(info["itemId"], {child_item_id for child_item_id, _, _ in edges_for_top})

    # Krok 3: podepnij pod TEN element podelementy odkryte w kroku 1a (BOM) — dopiero teraz
    # znamy jego item_id, niezależnie od tego, czy był nowy, czy już istniał w PDM.
    for child_item_id, qty, newly_created in edges_for_top:
        try:
            api_post_json(
                f"/items/{info['itemId']}/children", {"childId": child_item_id, "quantity": qty}
            )
        except Exception as e:
            QtWidgets.QMessageBox.warning(
                None, t("pdm_title"), t("link_subitem_failed", error=e)
            )
            continue

        if newly_created:
            # Utworzony wyłącznie jako efekt uboczny przetwarzania drzewa (zob.
            # process_assembly_tree) -- teraz prawidłowo zagnieżdżony pod TYM dokumentem,
            # ukryj go z korzenia projektu.
            try:
                api_patch_json(f"/items/{child_item_id}/visibility", {"showInTree": False})
            except Exception:
                pass

    if info.get("localRenamed"):
        local_line = t("local_renamed_line", path=doc.FileName)
    else:
        local_line = t("local_already_named_line", path=doc.FileName)

    # Bez okna "wysłano do PDM jako X". Raport z całego biegu składa teraz serwer przy
    # POST /api/progress/finish i zostawia go jako powiadomienie w przeglądarce — tam, gdzie
    # człowiek i tak patrzy, bo to w karcie wypełniał formularze. Okno powstawało za
    # przeglądarką i wisiało, czekając na kliknięcie, którego nikt nie widział (zgłoszone
    # z praktyki). Numer, wysłany plik i los lokalnego pliku zostają w Report View.
    App.Console.PrintMessage(
        f"EasyPDM: wyslano jako {info['itemNumber']}"
        + (f" razem z {len(edges_for_top)} podelementami" if edges_for_top else "")
        + f"; wyslano z: {info['newPath']}; {local_line}\n"
    )

    # JEDEN wyjątek, dla którego okno zostaje: komponenty już podpięte do PDM ze statusem
    # "sprawdzany"/"wydany". Takich makro NIGDY nie aktualizuje, więc jeśli ktoś zmienił taki
    # plik lokalnie, jego zmiana NIE poszła na serwer — a raport z listy plików tego nie
    # powie, bo z jego punktu widzenia nic się nie wydarzyło.
    if locked_matches and not _RUN["locked_shown"]:
        status_labels = {"sprawdzany": t("status_label_sprawdzany"), "wydany": t("status_label_wydany")}
        lines = "\n".join(
            f"- {number}({name}) -- {status_labels.get(status, status)}"
            for number, name, status in locked_matches
        )
        QtWidgets.QMessageBox.warning(
            None, t("pdm_title"), t("locked_components_tail", count=len(locked_matches), lines=lines).strip()
        )

    # Dokument nadrzędny leci jako ostatni, już po całym drzewie. Gdy listy nie ma
    # (pojedynczy dokument, bez drzewa złożenia), serwer odpowiada "matched": false i nic
    # się nie dzieje.
    progress_mark(TOP_DOCUMENT_PROGRESS_KEY, "done")
    progress_finish()


# Odpala się tylko, gdy faktycznie działa GUI FreeCAD (a nie np. freecadcmd/import
# do testów) — bez GUI i tak nie dałoby się pokazać okna dialogowego.
if App.GuiUp:
    run()
