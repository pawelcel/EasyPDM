# -*- coding: utf-8 -*-
"""
PdmUpload — makro FreeCAD do wysyłania aktywnego dokumentu do PdmSystem.

Instalacja / uruchomienie:
    Macro -> Macros... -> "Add path to macro path list" -> wskaż ten folder,
    albo po prostu "Execute macro from file" i wybierz ten plik bezpośrednio.
    Nie wymaga instalacji jako workbench.

Co robi (w tej kolejności):
    1. Zapisuje aktywny dokument na dysku (jeśli nie był jeszcze zapisany, prosi o
       wskazanie ścieżki przez natywne okno "Zapisz jako").
    2. Pyta, czy chodzi o **nowy** rekord w PDM, czy o wgranie pliku do **już
       istniejącego** — w drugim przypadku pozwala wpisać/wyszukać (Część/Złożenie
       z całej bazy, nie tylko bieżącego projektu — dokładnie jak w aplikacji webowej).
       Dla nowego rekordu: projekt PDM, element nadrzędny (opcjonalnie), typ
       (Część/Złożenie), nazwa, rodzaj (dla Części: Wykonywana/Zakupowa/Normalia/Klienta —
       dla Złożenia opcjonalnie, bez "Klienta") i zależne od niego pola (Wykonywana:
       Materiał; Zakupowa: Producent/Numer zamówieniowy 1 i 2/Masa; Normalia:
       Materiał/Norma; Klienta: brak dodatkowych pól) — te same reguły co
       PartPropertyForm/add-node-dialog w aplikacji webowej.
    2a. Dla istniejącego elementu ze statusem "wydany" (w tym statusie PDM nie pozwala
        dogrywać plików — sprawdzane też po stronie serwera): pyta, czy stworzyć nową
        rewizję. Odmowa → nic nie jest zapisywane. Zgoda → status zmienia się na
        "w pracy" (ten sam mechanizm co w aplikacji webowej), co podnosi numer rewizji.
    3. Nowy rekord: tworzy go w PDM (POST /api/projects/{id}/nodes). Dla obu trybów:
       KOPIUJE bieżący plik dokumentu do PDM pod nazwą "numer (nazwa).REWIZJA.rozszerzenie"
       — ten sam format numer/nazwa, w jakim PDM wyświetla Części/Złożenia wszędzie indziej
       (zob. itemDisplayLabel w froncie), plus rewizja jako WIELKA LITERA (A, B, C... — ta
       sama konwencja co revisionLabel() we froncie; numer w bazie zostaje liczbą, to czysto
       kwestia formatowania nazwy). LOKALNY plik, w miejscu gdzie został otwarty, NIE jest
       ruszany — nie jest ani przenoszony, ani usuwany (przyda się, gdy serwer PDM przestanie
       współdzielić dysk z klientem, np. po przeniesieniu do kontenera Docker). Jeśli magazyn
       PDM jest widoczny z tej maszyny (zob. GET /api/config), kopia trafia do WSPÓLNEGO
       folderu storage/components/ (jednego dla wszystkich projektów — Część/Złożenie bywa
       współdzielone jako komponent BOM między projektami) i jest REJESTROWANA
       (POST .../attachments/register, bez ponownego przesyłania przez HTTP — kopia już
       fizycznie leży w magazynie serwera). PDM ZACHOWUJE kopie poprzednich rewizji (np.
       "67 (nazwa).A.FCStd" zostaje, gdy powstaje rewizja B) — nadpisywana jest tylko kopia
       TEJ SAMEJ rewizji (powtórna wysyłka bez zmiany statusu). Jeśli magazyn jest
       nieosiągalny, kopia trafia przez zwykły upload HTTP (POST /api/items/{id}/attachments,
       ten sam mechanizm co dogrywanie plików CAD z panelu właściwości w aplikacji webowej).

Automatyczne wykrywanie złożenia:
    Jeśli aktywny dokument linkuje (App::Link — standardowy sposób budowania złożeń
    w workbenchu Assembly/Assembly4) do INNYCH, zapisanych plików .FCStd, makro PRZED
    otwarciem głównego okna pyta, czy wysłać całe drzewo automatycznie. Po zgodzie:
    schodzi rekurencyjnie w głąb (pod-złożenia też mogą linkować dalej), dla każdego
    jeszcze nie wysłanego komponentu pokazuje osobne, krótkie okno (typ/nazwa/rodzaj —
    te same pola i reguły co dla nowego elementu), i wysyła wszystko w kolejności
    LIŚCIE NAJPIERW, na końcu główny dokument, budując po drodze cały BOM (z ilością
    odczytaną z liczby odnośników do tego samego pliku — pojedyncze linki i wzorce/
    tablice linków liczą się razem). Komponent uznaje za "już wysłany", jeśli jego
    etykieta pasuje do formatu "numer (nazwa).REWIZJA" (ten sam, który makro samo nadaje
    po wysłaniu) I taki numer istnieje w PDM — wtedy tylko podpina go do BOM-u, bez
    tworzenia duplikatu. "Nie" na to pytanie wysyła TYLKO bieżący dokument, dokładnie jak
    dotychczas (bez podelementów).

Logowanie:
    PdmSystem.Api wymaga sesji (ciasteczko pdm_session) dla każdego wywołania poza
    POST /api/auth/login — to samo makro więc też się loguje. Przy pierwszym uruchomieniu
    (albo gdy zapisana sesja wygasła/została unieważniona) pojawia się okno logowania
    (nazwa użytkownika + hasło); token sesji trafia do tych samych preferencji FreeCAD co
    adres API (User parameter:BaseApp/PdmSystem), więc kolejne uruchomienia makra (także po
    restarcie FreeCAD) NIE proszą o ponowne logowanie, dopóki sesja jest ważna (30 dni, tak
    samo jak w aplikacji webowej). W głównym oknie "Wyślij do PDM" widać, kto jest zalogowany,
    i można się stamtąd wylogować (przycisk "Wyloguj") — kolejne uruchomienie makra od razu
    poprosi o ponowne zalogowanie.

Ograniczenia (świadomie poza zakresem pierwszej wersji):
    - Automatyczne wykrywanie złożenia działa tylko dla odnośników do ZEWNĘTRZNYCH,
      zapisanych plików (App::Link) — nie dla złożeń trzymanych w jednym pliku jako
      kontenery App::Part (te nie mają osobnych plików do wysłania osobno).
    - Rozpoznanie "już wysłanego" komponentu opiera się na etykiecie dokumentu — makro
      samo ją nadaje po wysłaniu, ale NIE zapisuje tej zmiany na dysk (żeby nie ruszać
      pliku użytkownika bez pytania), więc działa pewnie tylko w obrębie JEDNEJ sesji
      FreeCAD, chyba że dokument zostanie potem ręcznie zapisany. W nowej sesji, dla
      pliku nigdy ręcznie nie zapisanego po wysłaniu, makro zaproponuje utworzenie go
      w PDM jeszcze raz (duplikat) — trzeba to wtedy przerwać/skorygować ręcznie.
    - Kopiowanie/rejestrowanie pliku w folderze magazynu zakłada, że jest on widoczny
      w systemie plików tej maszyny (dziś: klient i serwer na tym samym dysku) — jeśli
      GET /api/config jest nieosiągalne albo ścieżka nie istnieje/nie da się do niej
      zapisać, kopia trafia do PDM zwykłym uploadem (kopia HTTP) — w tym trybie
      fallbackowym historia rewizji nie jest zachowywana (każda wysyłka nadpisuje
      poprzednią kopię po stronie PDM). W obu trybach lokalny plik zawsze zostaje
      nienaruszony w miejscu, gdzie go otwarto.
    - Adres API zapisywany jest w preferencjach FreeCAD (User parameter:BaseApp/PdmSystem),
      domyślnie http://localhost:5000/api.
"""

import json
import os
import re
import shutil
import uuid
from urllib import error, request

import FreeCAD as App

try:
    from PySide6 import QtCore, QtWidgets
except ImportError:
    try:
        from PySide2 import QtCore, QtWidgets
    except ImportError:
        from PySide import QtCore
        from PySide import QtGui as QtWidgets  # bardzo stare FreeCAD (Qt4)


PARAM_GROUP = "User parameter:BaseApp/PdmSystem"
DEFAULT_BASE_URL = "http://localhost:5000/api"
SESSION_COOKIE_NAME = "pdm_session"


class AuthError(RuntimeError):
    """Brak sesji albo sesja wygasła/została unieważniona — trzeba się (ponownie) zalogować.
    Odróżniona od zwykłego RuntimeError, żeby ensure_logged_in() wiedziało kiedy pokazać
    okno logowania, zamiast tylko wyświetlić czerwony komunikat błędu."""
    pass

# Dopasowuje własną konwencję nazewnictwa "numer (nazwa).REWIZJA" (nadawaną plikom/etykietom
# przez to samo makro po wysłaniu do PDM) — np. "76 (RewizjaTest).C". Jeśli dokument został
# ponownie otwarty z takiego pliku, nazwa/etykieta NIE jest już samą nazwą elementu, tylko
# tym pełnym formatem — trzeba wyłuskać numer, żeby rozpoznać, o który element chodzi.
_REVISION_NAME_PATTERN = re.compile(r"^(\d+)\s*\((.+)\)(?:\.[A-Za-z]+)?$")


def get_base_url():
    return App.ParamGet(PARAM_GROUP).GetString("ApiBaseUrl", DEFAULT_BASE_URL).rstrip("/")


def set_base_url(url):
    App.ParamGet(PARAM_GROUP).SetString("ApiBaseUrl", url.rstrip("/"))


def get_session_token():
    return App.ParamGet(PARAM_GROUP).GetString("SessionToken", "") or None


def set_session_token(token):
    App.ParamGet(PARAM_GROUP).SetString("SessionToken", token or "")


def get_saved_username():
    return App.ParamGet(PARAM_GROUP).GetString("SessionDisplayName", "") or None


def set_saved_username(name):
    App.ParamGet(PARAM_GROUP).SetString("SessionDisplayName", name or "")


def _auth_headers():
    token = get_session_token()
    return {"Cookie": f"{SESSION_COOKIE_NAME}={token}"} if token else {}


def _read_error_body(http_error):
    try:
        return http_error.read().decode("utf-8") or str(http_error)
    except Exception:
        return str(http_error)


def _raise_for_http_error(e):
    if e.code == 401:
        raise AuthError(_read_error_body(e))
    raise RuntimeError(_read_error_body(e))


def api_get(path):
    req = request.Request(get_base_url() + path, method="GET", headers=_auth_headers())
    try:
        with request.urlopen(req, timeout=10) as resp:
            body = resp.read().decode("utf-8")
            return json.loads(body) if body else None
    except error.HTTPError as e:
        _raise_for_http_error(e)
    except error.URLError as e:
        raise RuntimeError(f"Brak połączenia z {get_base_url()}: {e.reason}")


def api_post_json(path, payload):
    data = json.dumps(payload).encode("utf-8")
    headers = {"Content-Type": "application/json"}
    headers.update(_auth_headers())
    req = request.Request(get_base_url() + path, data=data, method="POST", headers=headers)
    try:
        with request.urlopen(req, timeout=15) as resp:
            body = resp.read().decode("utf-8")
            return json.loads(body) if body else None
    except error.HTTPError as e:
        _raise_for_http_error(e)
    except error.URLError as e:
        raise RuntimeError(f"Brak połączenia z {get_base_url()}: {e.reason}")


def api_upload_file(path, file_path, field_name="file", override_filename=None):
    boundary = f"----PdmUploadBoundary{uuid.uuid4().hex}"
    with open(file_path, "rb") as f:
        file_content = f.read()
    filename = override_filename or os.path.basename(file_path)

    parts = [
        f"--{boundary}\r\n".encode("utf-8"),
        f'Content-Disposition: form-data; name="{field_name}"; filename="{filename}"\r\n'.encode("utf-8"),
        b"Content-Type: application/octet-stream\r\n\r\n",
        file_content,
        f"\r\n--{boundary}--\r\n".encode("utf-8"),
    ]
    payload = b"".join(parts)

    headers = {"Content-Type": f"multipart/form-data; boundary={boundary}"}
    headers.update(_auth_headers())
    req = request.Request(get_base_url() + path, data=payload, method="POST", headers=headers)
    try:
        with request.urlopen(req, timeout=60) as resp:
            body = resp.read().decode("utf-8")
            return json.loads(body) if body else None
    except error.HTTPError as e:
        _raise_for_http_error(e)
    except error.URLError as e:
        raise RuntimeError(f"Brak połączenia z {get_base_url()}: {e.reason}")


def api_patch_json(path, payload):
    data = json.dumps(payload).encode("utf-8")
    headers = {"Content-Type": "application/json"}
    headers.update(_auth_headers())
    req = request.Request(get_base_url() + path, data=data, method="PATCH", headers=headers)
    try:
        with request.urlopen(req, timeout=15) as resp:
            body = resp.read().decode("utf-8")
            return json.loads(body) if body else None
    except error.HTTPError as e:
        _raise_for_http_error(e)
    except error.URLError as e:
        raise RuntimeError(f"Brak połączenia z {get_base_url()}: {e.reason}")


def api_register_attachment(item_id, file_path):
    """Rejestruje JUŻ ISTNIEJĄCY plik (już wewnątrz magazynu PDM) jako załącznik —
    bez przesyłania go drugi raz przez HTTP (zob. POST .../attachments/register)."""
    return api_post_json(f"/items/{item_id}/attachments/register", {"filePath": file_path})


def api_login(username, password):
    """Loguje się (POST /api/auth/login) i zapisuje token sesji w preferencjach FreeCAD —
    ten sam mechanizm co ApiBaseUrl, więc logowanie przetrwa restart FreeCAD, dopóki sesja
    jest ważna po stronie serwera (30 dni, tak samo jak w aplikacji webowej). Zwraca dict
    użytkownika ({"username", "displayName", "role", ...}, tak jak POST /api/auth/login)."""
    data = json.dumps({"username": username, "password": password}).encode("utf-8")
    req = request.Request(
        get_base_url() + "/auth/login", data=data, method="POST",
        headers={"Content-Type": "application/json"},
    )
    try:
        with request.urlopen(req, timeout=10) as resp:
            body = resp.read().decode("utf-8")
            user = json.loads(body) if body else {}
            set_cookie_header = resp.headers.get("Set-Cookie", "")
    except error.HTTPError as e:
        raise RuntimeError(_read_error_body(e))
    except error.URLError as e:
        raise RuntimeError(f"Brak połączenia z {get_base_url()}: {e.reason}")

    token = None
    for part in set_cookie_header.split(";"):
        part = part.strip()
        if part.startswith(f"{SESSION_COOKIE_NAME}="):
            token = part[len(SESSION_COOKIE_NAME) + 1:]
            break
    if not token:
        raise RuntimeError("Logowanie nie powiodło się — serwer nie zwrócił sesji.")

    set_session_token(token)
    set_saved_username(user.get("displayName") or user.get("username") or username)
    return user


def api_logout():
    """Unieważnia sesję po stronie serwera (POST /api/auth/logout) i zawsze czyści też
    lokalnie zapisany token — nawet jeśli wywołanie się nie powiedzie (np. brak połączenia),
    użytkownik i tak przestaje być "zalogowany" z punktu widzenia tego makra, więc kolejne
    uruchomienie poprosi o ponowne logowanie."""
    token = get_session_token()
    if token:
        req = request.Request(
            get_base_url() + "/auth/logout", method="POST", headers=_auth_headers()
        )
        try:
            request.urlopen(req, timeout=10)
        except Exception:
            pass
    set_session_token(None)
    set_saved_username(None)


def ensure_logged_in():
    """Sprawdza, czy zapisana sesja jest jeszcze ważna (GET /api/auth/me); jeśli jej nie ma
    albo wygasła/została unieważniona, pokazuje okno logowania. Zwraca True, jeśli po
    wywołaniu tej funkcji jest aktywna sesja (można kontynuować), False jeśli użytkownik
    anulował logowanie."""
    if get_session_token():
        try:
            api_get("/auth/me")
            return True
        except AuthError:
            set_session_token(None)  # token wygasł/nieważny — nie próbuj go już więcej
        except Exception:
            # Np. brak połączenia — nie blokujemy logowaniem na etapie samego sprawdzenia,
            # błąd i tak wypłynie czytelnie przy pierwszym realnym wywołaniu API.
            return True

    dlg = LoginDialog()
    return dlg.exec() == QtWidgets.QDialog.Accepted


def sanitize_filename(name):
    cleaned = re.sub(r'[\\/:*?"<>|]+', "_", name).strip()
    return cleaned or "bez_nazwy"


# Cztery rodzaje Części — dokładnie te same i w tej samej kolejności co PartKindSelect/
# add-node-dialog w aplikacji webowej. Złożenie ma te same rodzaje minus "Klienta" (patrz
# add-node-dialog.tsx — okno tworzenia złożenia nie oferuje tej opcji).
PART_KINDS = ["Wykonywana", "Zakupowa", "Normalia", "Klienta"]
ASSEMBLY_KINDS = ["Wykonywana", "Zakupowa", "Normalia"]


def kind_field_visibility(is_part, rodzaj):
    """Jedno źródło prawdy dla widoczności pól zależnych od typu/rodzaju — używane zarówno
    przez PdmUploadDialog (tryb "nowy element"), jak i NewComponentDialog (automatyczne
    wykrywanie złożenia), żeby te dwa miejsca nie mogły się rozjechać. Dokładnie te same
    reguły co PartPropertyForm/add-node-dialog w aplikacji webowej: Wykonywana -> Materiał;
    Zakupowa -> Producent/Numery zamówieniowe/Masa; Normalia -> Materiał/Norma; Klienta ->
    brak dodatkowych pól. Złożenie: Materiał/Masa zawsze widoczne razem, niezależnie od
    rodzaju; Norma dotyczy tylko Części."""
    wykonywana = rodzaj == "Wykonywana"
    zakupowa = rodzaj == "Zakupowa"
    normalia = rodzaj == "Normalia"
    return {
        "material": (wykonywana or normalia) if is_part else True,
        "mass": zakupowa if is_part else True,
        "purchase": is_part and zakupowa,
        "norm": is_part and normalia,
    }


def revision_label(n):
    """Rewizje jako wielkie litery zamiast cyfr: 1->A, 2->B, ..., 26->Z, 27->AA...
    (jak numeracja kolumn arkusza) — sama liczba w bazie (revisionNumber) się nie zmienia.
    Ta sama konwersja jest po stronie frontu w api/types.ts (revisionLabel)."""
    n = int(n)
    label = ""
    while n > 0:
        n, remainder = divmod(n - 1, 26)
        label = chr(65 + remainder) + label
    return label or "A"


def get_storage_root():
    """Pyta API o skonfigurowany StorageRoot — działa tylko, gdy magazyn jest
    widoczny w systemie plików tej maszyny (dziś: klient i serwer na tym samym
    dysku). Zwraca None, jeśli API nie odpowie albo ścieżka jest niedostępna."""
    try:
        config = api_get("/config")
        return config.get("storageRoot") if config else None
    except Exception:
        return None


# ============================================================
# Wykrywanie złożenia z App::Link (odnośniki do zewnętrznych, zapisanych plików .FCStd —
# standardowy sposób budowania złożeń w workbenchu Assembly/Assembly4). Pozwala wysłać całe
# drzewo złożenia jednym uruchomieniem makra: najpierw wszystkie części/pod-złożenia
# (liście najpierw), na końcu główny dokument.
# ============================================================
def _iter_external_link_targets(doc):
    """Zwraca dict {ścieżka_pliku: [freecad_document, łączna_ilość]} dla wszystkich
    App::Link w `doc` wskazujących na INNY, już zapisany dokument (linki wewnątrz tego
    samego dokumentu — np. wzorzec śrub w obrębie jednej części — są pomijane, bo nie mają
    osobnego pliku do wysłania). Ilość to suma po WSZYSTKICH linkach do tego samego pliku:
    zwykły (niearrayowy) App::Link ma ElementCount=0, co liczymy jako 1 sztukę; wzorzec/
    tablica linków (ElementCount>0) liczy się jako tyle sztuk, ile wskazuje ElementCount."""
    result = {}
    for obj in doc.Objects:
        if obj.TypeId != "App::Link":
            continue
        linked = getattr(obj, "LinkedObject", None)
        if linked is None:
            continue
        linked_doc = getattr(linked, "Document", None)
        if linked_doc is None or not linked_doc.FileName or linked_doc.FileName == doc.FileName:
            continue
        qty = getattr(obj, "ElementCount", 0) or 1
        qty = max(int(qty), 1)
        key = linked_doc.FileName
        if key not in result:
            result[key] = [linked_doc, 0]
        result[key][1] += qty
    return result


def discover_component_tree(top_doc):
    """Rekurencyjnie schodzi po App::Link dokumentu `top_doc` (i dalej w głąb, jeśli
    linkowany dokument sam ma dalsze linki). Zwraca:
        order — lista ścieżek plików odkrytych komponentów w kolejności "liście najpierw"
                (dzieci przed rodzicami), BEZ samego top_doc,
        docs  — dict {ścieżka_pliku: freecad_document} dla wszystkich odkrytych plików,
        edges — lista (ścieżka_rodzica, ścieżka_dziecka, ilość) dla WSZYSTKICH par
                rodzic-dziecko w drzewie, WŁĄCZNIE z tymi, gdzie rodzicem jest top_doc.
    `visited` chroni przed nieskończoną rekurencją, gdyby (nietypowo) powstał cykl."""
    order = []
    docs = {}
    edges = []
    visited = set()

    def visit(doc):
        if doc.FileName in visited:
            return
        visited.add(doc.FileName)
        for child_doc, qty in _iter_external_link_targets(doc).values():
            visit(child_doc)
            edges.append((doc.FileName, child_doc.FileName, qty))
        if doc.FileName != top_doc.FileName:
            docs[doc.FileName] = doc
            order.append(doc.FileName)

    visit(top_doc)
    return order, docs, edges


def match_existing_item(doc, existing_items):
    """Sprawdza, czy etykieta dokumentu wygląda jak "numer (nazwa).REWIZJA" — format,
    który to samo makro nadaje PO wysłaniu (zob. _rename_and_upload) — i jeśli tak, czy
    taki numer faktycznie istnieje w PDM. Zwraca dopasowany wpis (jak z GET /api/items)
    albo None, jeśli dokument trzeba dopiero utworzyć. Uwaga: to dopasowanie działa tylko
    w obrębie BIEŻĄCEJ sesji FreeCAD albo jeśli plik został ręcznie zapisany po
    zmianie etykiety — sama zmiana etykiety po wysłaniu NIE jest zapisywana na dysk
    (zob. komentarz w _rename_and_upload), więc ponowne otwarcie pliku w NOWEJ sesji
    FreeCAD bez wcześniejszego ręcznego zapisu pokaże oryginalną etykietę."""
    m = _REVISION_NAME_PATTERN.match(doc.Label)
    if not m:
        return None
    item_number = int(m.group(1))
    for it in existing_items:
        if it.get("itemNumber") == item_number:
            return it
    return None


def _usage_hint_for(file_path, edges):
    """Czytelny opis "używane Nx w pliku Y" do okna nowego komponentu — komponent może być
    używany w kilku miejscach drzewa naraz (współdzielona część)."""
    parts = [
        f"{qty}× w {os.path.basename(parent)}"
        for parent, child, qty in edges
        if child == file_path
    ]
    return "Używane: " + ", ".join(parts) if parts else ""


def _rename_and_upload(doc, item_id, item_number, name, revision):
    """Wspólna końcówka obu trybów: KOPIUJE bieżący plik dokumentu do PDM pod nazwą
    "numer (nazwa).REWIZJA.rozszerzenie" (ta sama konwencja numer/nazwa co itemDisplayLabel
    we froncie, plus litera rewizji — zob. revision_label). Lokalny plik, w miejscu gdzie
    został otwarty, NIE jest ruszany — nie jest ani przenoszony, ani usuwany (tylko etykieta
    dokumentu w FreeCAD się zmienia, co nie ma wpływu na dysk). Dzięki temu ten sam mechanizm
    będzie działał także wtedy, gdy serwer PDM przestanie współdzielić dysk z klientem (np.
    po przeniesieniu do kontenera Docker) — dziś to jeszcze zwykła kopia na tym samym dysku,
    ale nic nie zakłada, że lokalny plik i magazyn muszą leżeć w tym samym miejscu na stałe.

    Jeśli magazyn PDM jest osiągalny z tej maszyny (zob. GET /api/config): kopia trafia do
    WSPÓLNEGO folderu storage/components/ (jeden dla wszystkich projektów — Część/Złożenie
    bywa współdzielone jako komponent BOM między projektami) i jest REJESTROWANA
    (POST .../attachments/register, bez ponownego przesyłania przez HTTP — plik już fizycznie
    leży w magazynie serwera). PDM ZACHOWUJE kopie poprzednich rewizji (np. "67 (nazwa).A.FCStd"
    zostaje, gdy powstaje rewizja B) — nadpisywana jest tylko kopia TEJ SAMEJ rewizji, czyli
    powtórna wysyłka bez zmiany statusu. Jeśli magazyn nie jest osiągalny, kopia trafia przez
    zwykły upload HTTP (POST .../attachments) pod tą samą, ładną nazwą.

    Zwraca dict: {"itemId", "itemNumber", "newPath"} — "newPath" to ścieżka KOPII na serwerze
    (albo lokalny plik, jeśli magazyn jest nieosiągalny), NIE lokalny plik dokumentu."""
    ext = os.path.splitext(doc.FileName)[1]
    name_prefix = f"{item_number} ({sanitize_filename(name)})"
    new_filename = f"{name_prefix}.{revision_label(revision)}{ext}"

    doc.Label = f"{item_number} ({name}).{revision_label(revision)}"

    storage_root = get_storage_root()
    target_path = None
    if storage_root:
        components_dir = os.path.join(storage_root, "components")
        try:
            os.makedirs(components_dir, exist_ok=True)
            target_path = os.path.join(components_dir, new_filename)
            shutil.copy2(doc.FileName, target_path)
        except OSError:
            target_path = None  # magazyn niedostępny z tej maszyny — spadamy do zwykłego uploadu

    if target_path:
        # Jeśli kopia TEJ SAMEJ rewizji (dokładnie ta sama nazwa) jest już zarejestrowana,
        # nie trzeba nic robić — świeże bajty już tam leżą (shutil.copy2 nadpisał w miejscu),
        # a rejestrowanie drugi raz tej samej ścieżki i tak by się nie udało (unikalny
        # file_path w bazie). Załączniki innych rewizji (inna litera) zostają nietknięte —
        # to zachowana historia rewizji.
        try:
            existing = api_get(f"/items/{item_id}/attachments")
        except Exception:
            existing = []
        already_registered = any(a["fileName"] == new_filename for a in existing or [])
        if not already_registered:
            api_register_attachment(item_id, target_path)
        return {"itemId": item_id, "itemNumber": item_number, "newPath": target_path}

    api_upload_file(f"/items/{item_id}/attachments", doc.FileName, override_filename=new_filename)
    return {"itemId": item_id, "itemNumber": item_number, "newPath": doc.FileName}


def push_new_item_to_pdm(doc, project_id, item_type, name, properties, parent_id=None):
    """Tworzy NOWY element w PDM, a potem dogrywa bieżący dokument jako jego załącznik
    (zob. _rename_and_upload). Nowy element zawsze zaczyna od rewizji 1."""
    if not doc.FileName:
        raise RuntimeError("Dokument nie jest zapisany na dysku.")
    doc.save()

    body = {"name": name, "itemType": item_type, "properties": properties}
    if parent_id:
        body["parentId"] = parent_id

    created = api_post_json(f"/projects/{project_id}/nodes", body)
    return _rename_and_upload(doc, created["id"], created["itemNumber"], name, 1)


def push_to_existing_item(doc, item_id, confirm_new_revision):
    """Dogrywa bieżący dokument jako aktualny plik JUŻ ISTNIEJĄCEJ Części/Złożenia
    (np. nowa wersja po zmianach) — bez tworzenia nowego rekordu w PDM.

    Jeśli element ma status "wydany", w tym statusie nie da się dogrywać plików
    (backend blokuje to na wszelki wypadek, ale pytamy PRZED próbą, żeby nie kończyć się
    zwykłym błędem) — wywołuje `confirm_new_revision()` (funkcja bezargumentowa), pytając,
    czy stworzyć nową rewizję. Zwraca None, jeśli użytkownik odmówił — wtedy NIC nie jest
    zapisywane. W przeciwnym razie zwraca (możliwie pusty) tekst komentarza do rewizji.
    Status zmienia się na "w pracy" (PATCH /items/{id}/status — ten sam mechanizm co
    w aplikacji webowej, podnosi numer rewizji i opcjonalnie zapisuje komentarz), a dopiero
    potem plik trafia do PDM pod nazwą nowej rewizji."""
    if not doc.FileName:
        raise RuntimeError("Dokument nie jest zapisany na dysku.")
    doc.save()

    item = api_get(f"/items/{item_id}")
    revision = item.get("revisionNumber") or 1

    if item.get("status") == "wydany":
        comment = confirm_new_revision()
        if comment is None:
            return None
        status_result = api_patch_json(
            f"/items/{item_id}/status", {"status": "w_pracy", "comment": comment or None}
        )
        revision = (status_result or {}).get("revisionNumber") or (revision + 1)

    return _rename_and_upload(doc, item_id, item["itemNumber"], item["fileName"], revision)


class LoginDialog(QtWidgets.QDialog):
    """Logowanie do PdmSystem — pokazywane przez ensure_logged_in(), gdy nie ma jeszcze
    zapisanej sesji albo poprzednia wygasła/została unieważniona."""

    def __init__(self, parent=None):
        super().__init__(parent)
        self.setWindowTitle("Logowanie do PDM")
        self.setMinimumWidth(360)

        layout = QtWidgets.QVBoxLayout(self)
        form = QtWidgets.QFormLayout()
        layout.addLayout(form)

        self.server_edit = QtWidgets.QLineEdit(get_base_url())
        form.addRow("Adres API:", self.server_edit)

        self.username_edit = QtWidgets.QLineEdit()
        form.addRow("Nazwa użytkownika:", self.username_edit)

        self.password_edit = QtWidgets.QLineEdit()
        self.password_edit.setEchoMode(QtWidgets.QLineEdit.Password)
        form.addRow("Hasło:", self.password_edit)

        self.error_label = QtWidgets.QLabel("")
        self.error_label.setStyleSheet("color: #c0392b;")
        self.error_label.setWordWrap(True)
        layout.addWidget(self.error_label)

        buttons = QtWidgets.QDialogButtonBox(
            QtWidgets.QDialogButtonBox.Ok | QtWidgets.QDialogButtonBox.Cancel
        )
        buttons.button(QtWidgets.QDialogButtonBox.Ok).setText("Zaloguj")
        buttons.button(QtWidgets.QDialogButtonBox.Cancel).setText("Anuluj")
        buttons.accepted.connect(self._try_login)
        buttons.rejected.connect(self.reject)
        layout.addWidget(buttons)

    def _try_login(self):
        self.error_label.setText("")
        set_base_url(self.server_edit.text().strip())
        username = self.username_edit.text().strip()
        password = self.password_edit.text()
        if not username or not password:
            self.error_label.setText("Podaj nazwę użytkownika i hasło.")
            return
        try:
            api_login(username, password)
        except Exception as e:
            self.error_label.setText(str(e))
            return
        self.accept()


class NewRevisionDialog(QtWidgets.QDialog):
    """Pytanie o stworzenie nowej rewizji elementu o statusie "Wydany", z opcjonalnym
    komentarzem opisującym zmianę — ta sama treść, którą zapisuje aplikacja webowa."""

    def __init__(self, parent=None):
        super().__init__(parent)
        self.setWindowTitle("Nowa rewizja")
        self.setMinimumWidth(380)

        layout = QtWidgets.QVBoxLayout(self)

        label = QtWidgets.QLabel(
            'Ten element ma status "Wydany" — nie można do niego dogrywać plików.\n\n'
            'Czy chcesz stworzyć nową rewizję (status zmieni się na "W pracy")?'
        )
        label.setWordWrap(True)
        layout.addWidget(label)

        layout.addWidget(QtWidgets.QLabel("Komentarz do rewizji (opcjonalnie):"))
        self.comment_edit = QtWidgets.QPlainTextEdit()
        self.comment_edit.setFixedHeight(70)
        self.comment_edit.setPlaceholderText("Co zmieniło się w tej rewizji…")
        layout.addWidget(self.comment_edit)

        buttons = QtWidgets.QDialogButtonBox(
            QtWidgets.QDialogButtonBox.Ok | QtWidgets.QDialogButtonBox.Cancel
        )
        buttons.button(QtWidgets.QDialogButtonBox.Ok).setText("Stwórz rewizję")
        buttons.button(QtWidgets.QDialogButtonBox.Cancel).setText("Anuluj")
        buttons.accepted.connect(self.accept)
        buttons.rejected.connect(self.reject)
        layout.addWidget(buttons)

    def comment_text(self):
        return self.comment_edit.toPlainText().strip()


class NewComponentDialog(QtWidgets.QDialog):
    """Zbiera dane dla JEDNEGO automatycznie wykrytego, jeszcze nie istniejącego w PDM
    komponentu złożenia (część albo pod-złożenie) — pokazywane raz na każdy taki komponent,
    w kolejności "liście najpierw", zanim zostanie przetworzony plik, który go używa.
    Pola i ich widoczność to dokładnie ta sama logika co w PdmUploadDialog (tryb "nowy
    element"), tylko bez wyboru trybu/elementu nadrzędnego — te są tu z góry przesądzone
    (zawsze "nowy", rodzic dopina się automatycznie po utworzeniu)."""

    def __init__(self, file_path, suggested_name, suggested_is_assembly, usage_hint, projects, materials, parent=None):
        super().__init__(parent)
        self.setWindowTitle("Nowy komponent złożenia")
        self.setMinimumWidth(440)

        outer = QtWidgets.QVBoxLayout(self)

        header_text = f"<b>{os.path.basename(file_path)}</b>"
        if usage_hint:
            header_text += f"<br>{usage_hint}"
        header = QtWidgets.QLabel(header_text)
        header.setWordWrap(True)
        outer.addWidget(header)

        form = QtWidgets.QFormLayout()
        outer.addLayout(form)

        self.project_combo = QtWidgets.QComboBox()
        for p in projects:
            self.project_combo.addItem(p["name"], p["id"])
        form.addRow("Projekt:", self.project_combo)

        self.type_combo = QtWidgets.QComboBox()
        self.type_combo.addItems(["Część", "Złożenie"])
        self.type_combo.setCurrentIndex(1 if suggested_is_assembly else 0)
        self.type_combo.currentIndexChanged.connect(self.on_type_changed)
        form.addRow("Typ:", self.type_combo)

        self.name_edit = QtWidgets.QLineEdit(suggested_name)
        form.addRow("Nazwa:", self.name_edit)

        self.rodzaj_combo = QtWidgets.QComboBox()
        self.rodzaj_combo.currentIndexChanged.connect(self.on_rodzaj_changed)
        form.addRow("Rodzaj:", self.rodzaj_combo)

        self.material_label = QtWidgets.QLabel("Materiał:")
        self.material_combo = QtWidgets.QComboBox()
        self.material_combo.setEditable(True)
        self.material_combo.addItem("", "")
        for m in materials:
            self.material_combo.addItem(m["name"], m["name"])
        form.addRow(self.material_label, self.material_combo)

        self.mass_label = QtWidgets.QLabel("Masa [kg]:")
        self.mass_edit = QtWidgets.QLineEdit()
        form.addRow(self.mass_label, self.mass_edit)

        self.manufacturer_label = QtWidgets.QLabel("Producent:")
        self.manufacturer_edit = QtWidgets.QLineEdit()
        form.addRow(self.manufacturer_label, self.manufacturer_edit)

        self.order1_label = QtWidgets.QLabel("Numer zamówieniowy 1:")
        self.order1_edit = QtWidgets.QLineEdit()
        form.addRow(self.order1_label, self.order1_edit)

        self.order2_label = QtWidgets.QLabel("Numer zamówieniowy 2:")
        self.order2_edit = QtWidgets.QLineEdit()
        form.addRow(self.order2_label, self.order2_edit)

        self.norm_label = QtWidgets.QLabel("Norma:")
        self.norm_edit = QtWidgets.QLineEdit()
        form.addRow(self.norm_label, self.norm_edit)

        self.error_label = QtWidgets.QLabel("")
        self.error_label.setStyleSheet("color: #c0392b;")
        self.error_label.setWordWrap(True)
        outer.addWidget(self.error_label)

        buttons = QtWidgets.QDialogButtonBox(
            QtWidgets.QDialogButtonBox.Ok | QtWidgets.QDialogButtonBox.Cancel
        )
        buttons.accepted.connect(self._try_accept)
        buttons.rejected.connect(self.reject)
        outer.addWidget(buttons)

        self.on_type_changed()

    def on_type_changed(self):
        is_part = self.type_combo.currentText() == "Część"
        self.rodzaj_combo.blockSignals(True)
        self.rodzaj_combo.clear()
        if is_part:
            self.rodzaj_combo.addItems(PART_KINDS)
        else:
            self.rodzaj_combo.addItem("(nie wybrano)", "")
            for k in ASSEMBLY_KINDS:
                self.rodzaj_combo.addItem(k, k)
        self.rodzaj_combo.blockSignals(False)
        self.on_rodzaj_changed()

    def on_rodzaj_changed(self):
        is_part = self.type_combo.currentText() == "Część"
        rodzaj = self.rodzaj_combo.currentText()
        vis = kind_field_visibility(is_part, rodzaj)

        for w in (self.material_label, self.material_combo):
            w.setVisible(vis["material"])
        for w in (self.mass_label, self.mass_edit):
            w.setVisible(vis["mass"])
        for w in (
            self.manufacturer_label,
            self.manufacturer_edit,
            self.order1_label,
            self.order1_edit,
            self.order2_label,
            self.order2_edit,
        ):
            w.setVisible(vis["purchase"])
        for w in (self.norm_label, self.norm_edit):
            w.setVisible(vis["norm"])

    def _try_accept(self):
        self.error_label.setText("")
        if not self.project_combo.currentData():
            self.error_label.setText("Wybierz projekt.")
            return
        if not self.name_edit.text().strip():
            self.error_label.setText("Nazwa jest wymagana.")
            return
        is_part = self.type_combo.currentText() == "Część"
        rodzaj = self.rodzaj_combo.currentText()
        if is_part and rodzaj not in PART_KINDS:
            self.error_label.setText(
                "Dla Części wybierz rodzaj: Wykonywana, Zakupowa, Normalia albo Klienta."
            )
            return
        self.accept()

    def result_data(self):
        """Zwraca (project_id, item_type, name, properties) — do przekazania do
        push_new_item_to_pdm."""
        is_part = self.type_combo.currentText() == "Część"
        item_type = "part" if is_part else "assembly"
        rodzaj = self.rodzaj_combo.currentText()
        if rodzaj == "(nie wybrano)":
            rodzaj = ""

        properties = {}
        if rodzaj:
            properties["rodzaj"] = rodzaj
        if self.material_combo.isVisible():
            material = self.material_combo.currentText().strip()
            if material:
                properties["material"] = material
        if self.mass_edit.isVisible():
            mass = self.mass_edit.text().strip()
            if mass:
                properties["mass"] = mass
        if self.manufacturer_edit.isVisible():
            manufacturer = self.manufacturer_edit.text().strip()
            if manufacturer:
                properties["manufacturer"] = manufacturer
            order1 = self.order1_edit.text().strip()
            if order1:
                properties["orderNumber"] = order1
            order2 = self.order2_edit.text().strip()
            if order2:
                properties["orderNumber2"] = order2
        if self.norm_edit.isVisible():
            norm = self.norm_edit.text().strip()
            if norm:
                properties["norm"] = norm

        return (
            self.project_combo.currentData(),
            item_type,
            self.name_edit.text().strip(),
            properties,
        )


class PdmUploadDialog(QtWidgets.QDialog):
    def __init__(self, doc, parent=None):
        super().__init__(parent)
        self.doc = doc
        self.result_info = None
        self._existing_items = []

        self.setWindowTitle("Wyślij do PDM")
        self.setMinimumWidth(440)

        outer = QtWidgets.QVBoxLayout(self)

        top_form = QtWidgets.QFormLayout()
        outer.addLayout(top_form)

        self.server_edit = QtWidgets.QLineEdit(get_base_url())
        top_form.addRow("Adres API:", self.server_edit)

        account_row = QtWidgets.QHBoxLayout()
        self.account_label = QtWidgets.QLabel(f"Zalogowano jako: {get_saved_username() or '?'}")
        account_row.addWidget(self.account_label)
        logout_btn = QtWidgets.QPushButton("Wyloguj")
        logout_btn.clicked.connect(self.on_logout)
        account_row.addWidget(logout_btn)
        account_row.addStretch(1)
        top_form.addRow("Konto:", account_row)

        reload_btn = QtWidgets.QPushButton("Odśwież listy z serwera")
        reload_btn.clicked.connect(self.reload_lists)
        top_form.addRow("", reload_btn)

        self.mode_combo = QtWidgets.QComboBox()
        self.mode_combo.addItems(["Nowy element w PDM", "Istniejący element w PDM"])
        self.mode_combo.currentIndexChanged.connect(self.on_mode_changed)
        top_form.addRow("Tryb:", self.mode_combo)

        # --- Tryb: nowy element -----------------------------------------
        self.new_group = QtWidgets.QWidget()
        new_form = QtWidgets.QFormLayout(self.new_group)
        new_form.setContentsMargins(0, 0, 0, 0)
        outer.addWidget(self.new_group)

        self.project_combo = QtWidgets.QComboBox()
        self.project_combo.currentIndexChanged.connect(self.on_project_changed)
        new_form.addRow("Projekt:", self.project_combo)

        self.parent_combo = QtWidgets.QComboBox()
        new_form.addRow("Element nadrzędny:", self.parent_combo)

        self.type_combo = QtWidgets.QComboBox()
        self.type_combo.addItems(["Część", "Złożenie"])
        self.type_combo.currentIndexChanged.connect(self.on_type_changed)
        new_form.addRow("Typ:", self.type_combo)

        self.name_edit = QtWidgets.QLineEdit(doc.Label)
        self.name_edit.textChanged.connect(self._check_name_and_maybe_switch)
        new_form.addRow("Nazwa:", self.name_edit)

        self.rodzaj_combo = QtWidgets.QComboBox()
        self.rodzaj_combo.currentIndexChanged.connect(self.on_rodzaj_changed)
        new_form.addRow("Rodzaj:", self.rodzaj_combo)

        self.material_label = QtWidgets.QLabel("Materiał:")
        self.material_combo = QtWidgets.QComboBox()
        self.material_combo.setEditable(True)
        new_form.addRow(self.material_label, self.material_combo)

        self.mass_label = QtWidgets.QLabel("Masa [kg]:")
        self.mass_edit = QtWidgets.QLineEdit()
        new_form.addRow(self.mass_label, self.mass_edit)

        self.manufacturer_label = QtWidgets.QLabel("Producent:")
        self.manufacturer_edit = QtWidgets.QLineEdit()
        new_form.addRow(self.manufacturer_label, self.manufacturer_edit)

        self.order1_label = QtWidgets.QLabel("Numer zamówieniowy 1:")
        self.order1_edit = QtWidgets.QLineEdit()
        new_form.addRow(self.order1_label, self.order1_edit)

        self.order2_label = QtWidgets.QLabel("Numer zamówieniowy 2:")
        self.order2_edit = QtWidgets.QLineEdit()
        new_form.addRow(self.order2_label, self.order2_edit)

        self.norm_label = QtWidgets.QLabel("Norma:")
        self.norm_edit = QtWidgets.QLineEdit()
        new_form.addRow(self.norm_label, self.norm_edit)

        # --- Tryb: istniejący element ------------------------------------
        self.existing_group = QtWidgets.QWidget()
        existing_form = QtWidgets.QFormLayout(self.existing_group)
        existing_form.setContentsMargins(0, 0, 0, 0)
        outer.addWidget(self.existing_group)

        self.existing_combo = QtWidgets.QComboBox()
        self.existing_combo.setEditable(True)
        self.existing_combo.setInsertPolicy(QtWidgets.QComboBox.NoInsert)
        self.existing_combo.setMinimumContentsLength(30)
        existing_form.addRow("Element (Część/Złożenie z całej bazy):", self.existing_combo)
        existing_form.addRow(
            "", QtWidgets.QLabel("Zacznij pisać, żeby wyszukać po numerze albo nazwie.")
        )

        # --- Wspólne --------------------------------------------------------
        bottom_form = QtWidgets.QFormLayout()
        outer.addLayout(bottom_form)

        self.error_label = QtWidgets.QLabel("")
        self.error_label.setStyleSheet("color: #c0392b;")
        self.error_label.setWordWrap(True)
        bottom_form.addRow(self.error_label)

        buttons = QtWidgets.QDialogButtonBox(
            QtWidgets.QDialogButtonBox.Ok | QtWidgets.QDialogButtonBox.Cancel
        )
        buttons.accepted.connect(self.on_submit)
        buttons.rejected.connect(self.reject)
        bottom_form.addRow(buttons)

        self.on_type_changed()
        self.on_mode_changed()
        self.reload_lists()
        # Sprawdzamy od razu nazwę dokumentu — jeśli Część/Złożenie o tej nazwie już
        # istnieje w PDM, od razu przełączamy na tryb "Istniejący element".
        self._check_name_and_maybe_switch(doc.Label)

    # ------------------------------------------------------------------
    # Automatyczne wykrycie już istniejącego elementu po nazwie
    # ------------------------------------------------------------------
    def _check_name_and_maybe_switch(self, name):
        # Tylko PODPOWIADAMY (przełączamy tryb i zaznaczamy dopasowanie) — nigdy nie
        # wysyłamy niczego automatycznie. Użytkownik i tak musi kliknąć "Dodaj", więc
        # może w każdej chwili wrócić do "Nowy element", jeśli o to mu chodziło.
        name = name.strip()
        if not name:
            return

        # Plik/etykieta mogła już być w formacie "numer (nazwa).REWIZJA" — np. gdy dokument
        # został ponownie otwarty z pliku zapisanego wcześniej przez to samo makro. Wtedy
        # dopasowujemy po NUMERZE (jednoznaczny), a nie po całym tekście jako nazwie.
        number_match = _REVISION_NAME_PATTERN.match(name)
        if number_match:
            item_number = int(number_match.group(1))
            matches = [it for it in self._existing_items if it["itemNumber"] == item_number]
        else:
            matches = [it for it in self._existing_items if it["fileName"].strip().lower() == name.lower()]
        if not matches:
            return

        self.mode_combo.setCurrentIndex(1)
        if len(matches) == 1:
            idx = self.existing_combo.findData(matches[0]["id"])
            if idx >= 0:
                self.existing_combo.setCurrentIndex(idx)
        else:
            # Kilka elementów o tej samej nazwie (np. w różnych projektach) — zawężamy
            # wyszukiwanie do tej nazwy, ale wybór zostawiamy użytkownikowi.
            self.existing_combo.setCurrentIndex(-1)
            self.existing_combo.setEditText(name)

    def on_logout(self):
        api_logout()
        QtWidgets.QMessageBox.information(
            self, "PDM", "Wylogowano. Kolejne uruchomienie makra poprosi o ponowne zalogowanie."
        )
        self.reject()

    # ------------------------------------------------------------------
    # Ładowanie danych z serwera
    # ------------------------------------------------------------------
    def reload_lists(self):
        set_base_url(self.server_edit.text().strip())
        self.error_label.setText("")

        try:
            projects = api_get("/projects")
        except Exception as e:
            self.error_label.setText(f"Nie udało się pobrać projektów: {e}")
            projects = []
        self.project_combo.clear()
        for p in projects:
            self.project_combo.addItem(p["name"], p["id"])

        try:
            materials = api_get("/materials")
        except Exception:
            materials = []
        self.material_combo.clear()
        self.material_combo.addItem("", "")
        for m in materials:
            self.material_combo.addItem(m["name"], m["name"])

        # Część/Złożenie z CAŁEJ bazy (nie tylko bieżącego projektu) — ten sam komponent
        # może być współdzielony/wersjonowany niezależnie od tego, gdzie formalnie żyje.
        try:
            all_items = api_get("/items")
        except Exception as e:
            self.error_label.setText(f"Nie udało się pobrać listy elementów: {e}")
            all_items = []
        self._existing_items = [it for it in all_items if it["itemType"] in ("part", "assembly")]
        self.existing_combo.clear()
        labels = []
        for it in self._existing_items:
            label = f'{it["itemNumber"]} ({it["fileName"]})'
            labels.append(label)
            self.existing_combo.addItem(label, it["id"])
        completer = QtWidgets.QCompleter(labels, self.existing_combo)
        completer.setCaseSensitivity(QtCore.Qt.CaseInsensitive)
        completer.setFilterMode(QtCore.Qt.MatchContains)
        completer.setCompletionMode(QtWidgets.QCompleter.PopupCompletion)
        completer.activated.connect(self._on_existing_picked)
        self.existing_combo.setCompleter(completer)
        self.existing_combo.setCurrentIndex(-1)
        self.existing_combo.clearEditText()

        self.on_project_changed()

    def on_mode_changed(self):
        is_new = self.mode_combo.currentIndex() == 0
        self.new_group.setVisible(is_new)
        self.existing_group.setVisible(not is_new)

    def _on_existing_picked(self, text):
        # Wybór podpowiedzi z QCompleter nie zawsze sam ustawia currentIndex/currentData
        # edytowalnego QComboBox — dowiązujemy to ręcznie po dokładnym dopasowaniu tekstu.
        idx = self.existing_combo.findText(text)
        if idx >= 0:
            self.existing_combo.setCurrentIndex(idx)

    def on_project_changed(self):
        self.parent_combo.clear()
        self.parent_combo.addItem("Brak (poziom główny projektu)", None)

        project_id = self.project_combo.currentData()
        if not project_id:
            return
        try:
            items = api_get(f"/items?projectId={project_id}")
        except Exception as e:
            self.error_label.setText(f"Nie udało się pobrać elementów projektu: {e}")
            return
        # Do struktury można dodać coś tylko pod Folderem albo Złożeniem (Część/Plik są liśćmi).
        for it in items:
            if it["itemType"] == "folder":
                label = it["fileName"]
            elif it["itemType"] == "assembly":
                label = f'{it["itemNumber"]} ({it["fileName"]})'
            else:
                continue
            self.parent_combo.addItem(label, it["id"])

    # ------------------------------------------------------------------
    # Widoczność pól zależna od typu/rodzaju (odzwierciedla reguły z aplikacji webowej)
    # ------------------------------------------------------------------
    def on_type_changed(self):
        is_part = self.type_combo.currentText() == "Część"
        self.rodzaj_combo.blockSignals(True)
        self.rodzaj_combo.clear()
        if is_part:
            self.rodzaj_combo.addItems(PART_KINDS)
        else:
            # Złożenie: rodzaj jest opcjonalny i nie ma "Klienta" (tak samo jak w oknie
            # tworzenia złożenia w aplikacji webowej).
            self.rodzaj_combo.addItem("(nie wybrano)", "")
            for k in ASSEMBLY_KINDS:
                self.rodzaj_combo.addItem(k, k)
        self.rodzaj_combo.blockSignals(False)
        self.on_rodzaj_changed()

    def on_rodzaj_changed(self):
        is_part = self.type_combo.currentText() == "Część"
        rodzaj = self.rodzaj_combo.currentText()
        vis = kind_field_visibility(is_part, rodzaj)

        for w in (self.material_label, self.material_combo):
            w.setVisible(vis["material"])
        for w in (self.mass_label, self.mass_edit):
            w.setVisible(vis["mass"])
        for w in (
            self.manufacturer_label,
            self.manufacturer_edit,
            self.order1_label,
            self.order1_edit,
            self.order2_label,
            self.order2_edit,
        ):
            w.setVisible(vis["purchase"])
        for w in (self.norm_label, self.norm_edit):
            w.setVisible(vis["norm"])

    # ------------------------------------------------------------------
    # Zapis
    # ------------------------------------------------------------------
    def on_submit(self):
        self.error_label.setText("")

        if self.mode_combo.currentIndex() == 1:
            self._submit_existing()
        else:
            self._submit_new()

    def _submit_existing(self):
        item_id = self.existing_combo.currentData()
        if not item_id:
            # Użytkownik mógł wpisać dokładny tekst ręcznie, bez klikania w podpowiedź.
            idx = self.existing_combo.findText(self.existing_combo.currentText().strip())
            if idx >= 0:
                item_id = self.existing_combo.itemData(idx)
        if not item_id:
            self.error_label.setText("Wybierz element z listy (Część albo Złożenie).")
            return

        def confirm_new_revision():
            dlg = NewRevisionDialog(self)
            if dlg.exec() != QtWidgets.QDialog.Accepted:
                return None
            return dlg.comment_text()

        try:
            # None oznacza: element był "Wydany", a użytkownik odmówił nowej rewizji —
            # nic nie zostało zapisane, ale to nie jest błąd.
            self.result_info = push_to_existing_item(self.doc, item_id, confirm_new_revision)
        except Exception as e:
            self.error_label.setText(str(e))
            return

        self.accept()

    def _submit_new(self):
        project_id = self.project_combo.currentData()
        if not project_id:
            self.error_label.setText("Wybierz projekt.")
            return

        item_type = "part" if self.type_combo.currentText() == "Część" else "assembly"
        name = self.name_edit.text().strip()
        if not name:
            self.error_label.setText("Nazwa jest wymagana.")
            return

        rodzaj = self.rodzaj_combo.currentText()
        if item_type == "part" and rodzaj not in PART_KINDS:
            self.error_label.setText(
                "Dla Części wybierz rodzaj: Wykonywana, Zakupowa, Normalia albo Klienta."
            )
            return
        if rodzaj == "(nie wybrano)":
            rodzaj = ""

        properties = {}
        if rodzaj:
            properties["rodzaj"] = rodzaj

        if self.material_combo.isVisible():
            material = self.material_combo.currentText().strip()
            if material:
                properties["material"] = material
        if self.mass_edit.isVisible():
            mass = self.mass_edit.text().strip()
            if mass:
                properties["mass"] = mass
        if self.manufacturer_edit.isVisible():
            manufacturer = self.manufacturer_edit.text().strip()
            if manufacturer:
                properties["manufacturer"] = manufacturer
            order1 = self.order1_edit.text().strip()
            if order1:
                properties["orderNumber"] = order1
            order2 = self.order2_edit.text().strip()
            if order2:
                properties["orderNumber2"] = order2
        if self.norm_edit.isVisible():
            norm = self.norm_edit.text().strip()
            if norm:
                properties["norm"] = norm

        parent_id = self.parent_combo.currentData()

        try:
            self.result_info = push_new_item_to_pdm(
                self.doc, project_id, item_type, name, properties, parent_id
            )
        except Exception as e:
            self.error_label.setText(str(e))
            return

        self.accept()


def process_assembly_tree(top_doc):
    """Wykrywa złożenie (App::Link do zewnętrznych plików, rekurencyjnie) i dla KAŻDEGO
    nowego komponentu (jeszcze nie wysłanego do PDM — rozpoznawane po etykiecie
    "numer (nazwa).REWIZJA", zob. match_existing_item) pokazuje NewComponentDialog, tworzy
    go w PDM, po czym podpina relacje rodzic-dziecko (BOM) MIĘDZY odkrytymi komponentami.
    Relacje, gdzie rodzicem jest top_doc, NIE są tu podpinane — top_doc jeszcze nie ma
    swojego item_id w PDM (może to być nowy ALBO już istniejący element — o tym decyduje
    reszta run() przez zwykły PdmUploadDialog); te relacje dopina run() po jego utworzeniu.

    Zwraca (edges_for_top, cancelled):
        edges_for_top — lista (child_item_id, quantity) do podpięcia pod element top_doc,
        cancelled     — True, jeśli użytkownik przerwał w trakcie. Komponenty utworzone
                        PRZED przerwaniem zostają w PDM (tak samo jak reszta makra nie
                        cofa częściowo wykonanych kroków w razie błędu w połowie)."""
    order, docs, edges = discover_component_tree(top_doc)
    if not order:
        return [], False

    summary = "\n".join(f"- {os.path.basename(f)}" for f in order)
    choice = QtWidgets.QMessageBox.question(
        None,
        "Wykryto złożenie",
        f"Ten dokument linkuje do {len(order)} innych plików (części/pod-złożeń):\n\n"
        f"{summary}\n\n"
        "Wysłać je automatycznie razem z tym dokumentem (najpierw części/pod-złożenia, "
        "na końcu ten dokument)?\n\n"
        "\"Nie\" wyśle TYLKO ten dokument, tak jak dotychczas — bez podelementów.",
        QtWidgets.QMessageBox.Yes | QtWidgets.QMessageBox.No | QtWidgets.QMessageBox.Cancel,
        QtWidgets.QMessageBox.Yes,
    )
    if choice == QtWidgets.QMessageBox.Cancel:
        return [], True
    if choice == QtWidgets.QMessageBox.No:
        return [], False

    try:
        existing_items = api_get("/items") or []
    except Exception as e:
        QtWidgets.QMessageBox.warning(None, "PDM", f"Nie udało się pobrać listy elementów: {e}")
        existing_items = []
    try:
        projects = api_get("/projects") or []
    except Exception as e:
        QtWidgets.QMessageBox.critical(None, "PDM", f"Nie udało się pobrać listy projektów: {e}")
        return [], True
    try:
        materials = api_get("/materials") or []
    except Exception:
        materials = []

    # Pliki, które same mają dalsze zewnętrzne linki -> podpowiadamy w oknie typ "Złożenie".
    has_children = {parent for parent, _child, _qty in edges}

    doc_to_item_id = {}
    for file_path in order:
        doc = docs[file_path]
        matched = match_existing_item(doc, existing_items)
        if matched:
            doc_to_item_id[file_path] = matched["id"]
            continue

        dlg = NewComponentDialog(
            file_path=file_path,
            suggested_name=doc.Label,
            suggested_is_assembly=file_path in has_children,
            usage_hint=_usage_hint_for(file_path, edges),
            projects=projects,
            materials=materials,
        )
        if dlg.exec() != QtWidgets.QDialog.Accepted:
            return [], True

        project_id, item_type, name, properties = dlg.result_data()
        try:
            result = push_new_item_to_pdm(doc, project_id, item_type, name, properties)
        except Exception as e:
            QtWidgets.QMessageBox.critical(
                None, "PDM", f"Nie udało się wysłać {os.path.basename(file_path)}: {e}"
            )
            return [], True
        doc_to_item_id[file_path] = result["itemId"]

    edges_for_top = []
    for parent_file, child_file, qty in edges:
        child_item_id = doc_to_item_id.get(child_file)
        if child_item_id is None:
            continue
        if parent_file == top_doc.FileName:
            edges_for_top.append((child_item_id, qty))
            continue
        parent_item_id = doc_to_item_id.get(parent_file)
        if parent_item_id is None:
            continue
        try:
            api_post_json(
                f"/items/{parent_item_id}/children", {"childId": child_item_id, "quantity": qty}
            )
        except Exception as e:
            QtWidgets.QMessageBox.warning(
                None,
                "PDM",
                f"Utworzono {os.path.basename(child_file)}, ale nie udało się podpiąć go "
                f"pod {os.path.basename(parent_file)}: {e}",
            )

    return edges_for_top, False


def run():
    # Krok 0: upewnij się, że jest aktywna sesja — PdmSystem.Api wymaga jej dla każdego
    # wywołania poza samym logowaniem.
    if not ensure_logged_in():
        return  # użytkownik anulował logowanie

    doc = App.ActiveDocument
    if doc is None:
        QtWidgets.QMessageBox.warning(None, "PDM", "Brak otwartego dokumentu.")
        return

    # Krok 1: zapisz element przed wrzuceniem do PDM.
    if not doc.FileName:
        QtWidgets.QMessageBox.information(
            None, "PDM", "Dokument nie jest jeszcze zapisany — wskaż, gdzie go zapisać."
        )
        import FreeCADGui as Gui

        Gui.runCommand("Std_SaveAs")
        if not doc.FileName:
            return  # użytkownik anulował zapis
    else:
        doc.save()

    # Krok 1a: wykryj i (opcjonalnie) wyślij złożenie rekurencyjnie — części/pod-złożenia
    # znalezione przez App::Link, w kolejności liście-najpierw.
    edges_for_top, cancelled = process_assembly_tree(doc)
    if cancelled:
        QtWidgets.QMessageBox.information(None, "PDM", "Przerwano — anulowano wysyłkę.")
        return

    # Krok 2: uzupełnienie danych w oknie dialogowym (tworzy element + dogrywa plik + zmienia nazwę).
    dialog = PdmUploadDialog(doc)
    if dialog.exec() != QtWidgets.QDialog.Accepted:
        return

    if dialog.result_info is None:
        # Element był "Wydany", a użytkownik odmówił stworzenia nowej rewizji.
        QtWidgets.QMessageBox.information(None, "PDM", "Anulowano — nic nie zostało wysłane.")
        return

    info = dialog.result_info

    # Krok 3: podepnij pod TEN element podelementy odkryte w kroku 1a (BOM) — dopiero teraz
    # znamy jego item_id, niezależnie od tego, czy był nowy, czy już istniał w PDM.
    for child_item_id, qty in edges_for_top:
        try:
            api_post_json(
                f"/items/{info['itemId']}/children", {"childId": child_item_id, "quantity": qty}
            )
        except Exception as e:
            QtWidgets.QMessageBox.warning(
                None, "PDM", f"Nie udało się podpiąć jednego z podelementów pod główny element: {e}"
            )

    QtWidgets.QMessageBox.information(
        None,
        "PDM",
        f"Wysłano do PDM jako {info['itemNumber']}"
        + (f" razem z {len(edges_for_top)} podelementami" if edges_for_top else "")
        + ".\n"
        f"Kopia w magazynie PDM:\n{info['newPath']}\n\n"
        f"Lokalny plik pozostał bez zmian:\n{doc.FileName}",
    )


# Odpala się tylko, gdy faktycznie działa GUI FreeCAD (a nie np. freecadcmd/import
# do testów) — bez GUI i tak nie dałoby się pokazać okna dialogowego.
if App.GuiUp:
    run()
